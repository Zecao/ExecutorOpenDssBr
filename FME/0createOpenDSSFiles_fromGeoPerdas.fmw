FME workspace 0createOpenDSSFiles_fromGeoPerdas.fmw

Parameters:
- CodDist = 18   # Digite o codigo da Distribuidora
- CodBase = 4950   # Digite a CodBase
- Ano = 2016   # Digite Ano
- DatBas = 20180426183300   # Digite Data Base
- SourceDataset_MSSQL_ADO = GEOPERDAS_DAIMON2018   # SQL Server Connection
- SourceDataset_CSV = Alim_gdis_OpenDSS.txt   # Source CSV (Comma Separated Value) File(s)
- SourceDataset_XLSXR_6 = recursos\curvasDeCargaAccess.xlsx   # Source Microsoft Excel File(s)
- boolFiltraTrafoVazio = 0
- DestDataset_TEXTLINE_66 = D:\PROGGEOPERDAS_V2016-11-25\saida   # Destination Text File
- DestDataset_TEXTLINE = D:\PROGGEOPERDAS_V2016-11-25\saida   # Destination Text File
- DestDataset_TEXTLINE_50 = D:\PROGGEOPERDAS_V2016-11-25\saida   # Destination Text File
- DestDataset_TEXTLINE_74 = D:\PROGGEOPERDAS_V2016-11-25\saida   # Destination Text File
- DestDataset_TEXTLINE_58 = D:\PROGGEOPERDAS_V2016-11-25\saida   # Destination Text File
- DestDataset_TEXTLINE_82 = D:\PROGGEOPERDAS_V2016-11-25\saida   # Destination Text File
- DestDataset_TEXTLINE_54 = D:\PROGGEOPERDAS_V2016-11-25\saida   # Destination Text File
- DestDataset_TEXTLINE_62 = D:\PROGGEOPERDAS_V2016-11-25\saida   # Destination Text File
- DestDataset_TEXTLINE_70 = D:\PROGGEOPERDAS_V2016-11-25\saida   # Destination Text File
- DestDataset_TEXTLINE_78 = D:\PROGGEOPERDAS_V2016-11-25\saida   # Destination Text File
- DestDataset_TEXTLINE_48 = D:\PROGGEOPERDAS_V2016-11-25\saida   # Destination Text File
- DestDataset_TEXTLINE_52 = D:\PROGGEOPERDAS_V2016-11-25\saida   # Destination Text File
- DestDataset_TEXTLINE_56 = D:\PROGGEOPERDAS_V2016-11-25\saida   # Destination Text File
- DestDataset_TEXTLINE_60 = D:\PROGGEOPERDAS_V2016-11-25\saida   # Destination Text File
- DestDataset_TEXTLINE_64 = D:\PROGGEOPERDAS_V2016-11-25\saida   # Destination Text File
- DestDataset_TEXTLINE_68 = D:\PROGGEOPERDAS_V2016-11-25\saida   # Destination Text File
- DestDataset_TEXTLINE_72 = D:\PROGGEOPERDAS_V2016-11-25\saida   # Destination Text File
- DestDataset_TEXTLINE_76 = D:\PROGGEOPERDAS_V2016-11-25\saida   # Destination Text File
- DestDataset_TEXTLINE_80 = D:\PROGGEOPERDAS_V2016-11-25\saida   # Destination Text File
- DestDataset_TEXTLINE_84 = D:\PROGGEOPERDAS_V2016-11-25\saida   # Destination Text File
- DestDataset_TEXTLINE_49 = D:\PROGGEOPERDAS_V2016-11-25\saida   # Destination Text File
- DestDataset_TEXTLINE_51 = D:\PROGGEOPERDAS_V2016-11-25\saida   # Destination Text File
- DestDataset_TEXTLINE_53 = D:\PROGGEOPERDAS_V2016-11-25\saida   # Destination Text File
- DestDataset_TEXTLINE_55 = D:\PROGGEOPERDAS_V2016-11-25\saida   # Destination Text File
- DestDataset_TEXTLINE_57 = D:\PROGGEOPERDAS_V2016-11-25\saida   # Destination Text File
- DestDataset_TEXTLINE_59 = D:\PROGGEOPERDAS_V2016-11-25\saida   # Destination Text File
- DestDataset_CSV = $(FME_MF_DIR_USERTYPED)   # Destination CSV (CommaSeparatedValue) Folder
- DestDataset_TEXTLINE_65 = D:\PROGGEOPERDAS_V2016-11-25\saida   # Destination Text File
- DestDataset_TEXTLINE_63 = D:\PROGGEOPERDAS_V2016-11-25\saida   # Destination Text File
- DestDataset_TEXTLINE_61 = D:\PROGGEOPERDAS_V2016-11-25\saida   # Destination Text File
- DestDataset_TEXTLINE_67 = D:\PROGGEOPERDAS_V2016-11-25\saida   # Destination Text File
- DestDataset_TEXTLINE_69 = D:\PROGGEOPERDAS_V2016-11-25\saida   # Destination Text File
- DestDataset_TEXTLINE_71 = D:\PROGGEOPERDAS_V2016-11-25\saida   # Destination Text File
- DestDataset_TEXTLINE_73 = D:\PROGGEOPERDAS_V2016-11-25\saida   # Destination Text File
- DestDataset_TEXTLINE_75 = D:\PROGGEOPERDAS_V2016-11-25\saida   # Destination Text File
- DestDataset_TEXTLINE_77 = D:\PROGGEOPERDAS_V2016-11-25\saida   # Destination Text File
- DestDataset_TEXTLINE_79 = D:\PROGGEOPERDAS_V2016-11-25\saida   # Destination Text File
- DestDataset_TEXTLINE_81 = D:\PROGGEOPERDAS_V2016-11-25\saida   # Destination Text File
- DestDataset_TEXTLINE_83 = D:\PROGGEOPERDAS_V2016-11-25\saida   # Destination Text File
- SourceDataset_XLSXR = recursos\geracaoDistribuidaMT_Diaria_01_2016.xlsx   # Source Microsoft Excel File(s)

Readers:
- MSSQL_ADO_1: MSSQL_ADO from $(SourceDataset_MSSQL_ADO)
- CSV_1: CSV from $(SourceDataset_CSV)
- XLSXR_1: XLSXR from $(SourceDataset_XLSXR_6)
- XLSXR_2: XLSXR from $(SourceDataset_XLSXR)

Writers:
- MSSQL_ADO_2: MSSQL_ADO to GEOPERDAS_DAIMON2018
- TEXTLINE_1: TEXTLINE to D:\PROGGEOPERDAS_V2016-11-25\saida
- TEXTLINE_2: TEXTLINE to D:\PROGGEOPERDAS_V2016-11-25\saida
- TEXTLINE_3: TEXTLINE to D:\PROGGEOPERDAS_V2016-11-25\saida
- TEXTLINE_4: TEXTLINE to D:\PROGGEOPERDAS_V2016-11-25\saida
- TEXTLINE_5: TEXTLINE to D:\PROGGEOPERDAS_V2016-11-25\saida
- TEXTLINE_6: TEXTLINE to D:\PROGGEOPERDAS_V2016-11-25\saida
- TEXTLINE_7: TEXTLINE to D:\PROGGEOPERDAS_V2016-11-25\saida
- TEXTLINE_8: TEXTLINE to D:\PROGGEOPERDAS_V2016-11-25\saida
- TEXTLINE_9: TEXTLINE to D:\PROGGEOPERDAS_V2016-11-25\saida
- TEXTLINE_10: TEXTLINE to $(DestDataset_TEXTLINE_66)
- TEXTLINE_11: TEXTLINE to $(DestDataset_TEXTLINE)
- TEXTLINE_12: TEXTLINE to $(DestDataset_TEXTLINE_50)
- TEXTLINE_13: TEXTLINE to $(DestDataset_TEXTLINE_74)
- TEXTLINE_14: TEXTLINE to $(DestDataset_TEXTLINE_58)
- TEXTLINE_15: TEXTLINE to $(DestDataset_TEXTLINE_82)
- TEXTLINE_16: TEXTLINE to $(DestDataset_TEXTLINE_54)
- TEXTLINE_17: TEXTLINE to $(DestDataset_TEXTLINE_62)
- TEXTLINE_18: TEXTLINE to $(DestDataset_TEXTLINE_70)
- TEXTLINE_19: TEXTLINE to $(DestDataset_TEXTLINE_78)
- TEXTLINE_20: TEXTLINE to $(DestDataset_TEXTLINE_48)
- TEXTLINE_21: TEXTLINE to $(DestDataset_TEXTLINE_52)
- TEXTLINE_22: TEXTLINE to $(DestDataset_TEXTLINE_56)
- TEXTLINE_23: TEXTLINE to $(DestDataset_TEXTLINE_60)
- TEXTLINE_24: TEXTLINE to $(DestDataset_TEXTLINE_64)
- TEXTLINE_25: TEXTLINE to $(DestDataset_TEXTLINE_68)
- TEXTLINE_26: TEXTLINE to $(DestDataset_TEXTLINE_72)
- TEXTLINE_27: TEXTLINE to $(DestDataset_TEXTLINE_76)
- TEXTLINE_28: TEXTLINE to $(DestDataset_TEXTLINE_80)
- TEXTLINE_29: TEXTLINE to $(DestDataset_TEXTLINE_84)
- TEXTLINE_30: TEXTLINE to $(DestDataset_TEXTLINE_49)
- TEXTLINE_31: TEXTLINE to $(DestDataset_TEXTLINE_51)
- TEXTLINE_32: TEXTLINE to $(DestDataset_TEXTLINE_53)
- TEXTLINE_33: TEXTLINE to $(DestDataset_TEXTLINE_55)
- TEXTLINE_34: TEXTLINE to $(DestDataset_TEXTLINE_57)
- TEXTLINE_35: TEXTLINE to $(DestDataset_TEXTLINE_59)
- CSV_2: CSV to $(DestDataset_CSV)
- TEXTLINE_36: TEXTLINE to $(DestDataset_TEXTLINE_65)
- TEXTLINE_37: TEXTLINE to $(DestDataset_TEXTLINE_63)
- TEXTLINE_38: TEXTLINE to $(DestDataset_TEXTLINE_61)
- TEXTLINE_39: TEXTLINE to $(DestDataset_TEXTLINE_67)
- TEXTLINE_40: TEXTLINE to $(DestDataset_TEXTLINE_69)
- TEXTLINE_41: TEXTLINE to $(DestDataset_TEXTLINE_71)
- TEXTLINE_42: TEXTLINE to $(DestDataset_TEXTLINE_73)
- TEXTLINE_43: TEXTLINE to $(DestDataset_TEXTLINE_75)
- TEXTLINE_44: TEXTLINE to $(DestDataset_TEXTLINE_77)
- TEXTLINE_45: TEXTLINE to $(DestDataset_TEXTLINE_79)
- TEXTLINE_46: TEXTLINE to $(DestDataset_TEXTLINE_81)
- TEXTLINE_47: TEXTLINE to $(DestDataset_TEXTLINE_83)

Note: CSV: Alim_gdis_rodar [CSV]
CSV (reader CSV_1)
    attributes: Alim char(10)
    -> Counter
Counter
    DOMAIN = counter
    SCOPE = Global
    CNT_ATTR = _count
    START = 1
    -> Tester
Note: Informar número de alimentadores
Tester
    TEST_DESCRIPTION = ""
    TEST_MODE = Automatic
    TEST_CLAUSE = TEST @Value(_count) < 33
    BOOL_OP = OR
    PASSED -> StringReplacer_3
    PASSED -> escreveAlimDSS_2 [Alim]
    FAILED -> Alim_gdis_OpenDSS (writer CSV_2)
Note: RETIRA ESPAÇO ALIMENTADOR
StringReplacer_3
    REGEXP = no
    SRC_ATTRS = Alim
    FIND_TEXT = " "
    NO_MATCH = _FME_NO_OP_
    CASE = no
    -> AttributeCreator_14
Note: CodBase
AttributeCreator_14
    ATTR_LIST = CodBase,$(CodBase)
    -> SEGMENTO_BT [INITIATOR]
    -> SEGMENTO_MT_2 [INITIATOR]
    -> REGULADOR [INITIATOR]
    -> Chave [INITIATOR]
    -> Ramal [INITIATOR]
    -> Transformador [INITIATOR]
    -> PostoTransformador [INITIATOR]
    -> Consumo_Clientes_2 [INITIATOR]
    -> Clientes_MT [INITIATOR]
    -> verificaGDMT_Anual [verificaGDMT_FeatureMerger_Supplier_1]
SEGMENTO_BT: SQLExecutor
    MSSQL_ADO_QUERY_FEATURE_TYPES_FOR_MERGE_FILTERS = Yes
    MSSQL_ADO_COMMAND_TIMEOUT = 1000
    DATASET = GEOPERDAS_DAIMON2018
    COMBINE_ATTRS = Result Attributes Only
    EXPOSED_ATTRIBUTE_LIST = CodSegmBT,CodPonAcopl1,CodPonAcopl2,CodFas,CodCond,Comp_km,CodAlim
    SQL_STATEMENT:
      select * from StoredSegmentoBT
      where CodAlim in (@Value(Alim)) and CodBase = @Value(CodBase)
    COMBINE_GEOM = Initiator Geometry Only
    FORMAT = MSSQL_ADO
    MSSQL_ADO_NAMED_CONNECTION = GEOPERDAS_ANEEL_PROD
    RESULT -> escreveSegmentoBT
escreveSegmentoBT
    CODPONACOPL2 = @Value(CodPonAcopl2)
    CODPONACOPL1 = @Value(CodPonAcopl1)
    CODFAS = @Value(CodFas)
    CODCOND = @Value(CodCond)
    CODALIM = @Value(CodAlim)
    CODSEGMBT = @Value(CodSegmBT)
    COMP_KM = @Value(Comp_km)
    -> text_line (writer TEXTLINE_3)
    -> escreveAlimDSS_2 [segmentoBT]
text_line (writer TEXTLINE_3)
    attributes: text_line_data buffer
SEGMENTO_MT_2: SQLExecutor
    MSSQL_ADO_QUERY_FEATURE_TYPES_FOR_MERGE_FILTERS = Yes
    MSSQL_ADO_COMMAND_TIMEOUT = 100
    DATASET = GEOPERDAS_DAIMON2018
    COMBINE_ATTRS = Keep Result Attributes if Conflict
    EXPOSED_ATTRIBUTE_LIST = CodSegmMT,CodAlim,CodPonAcopl1,CodPonAcopl2,CodFas,CodCond,Comp_km
    SQL_STATEMENT:
      Select * from StoredSegmentoMT
      where CodAlim in (@Value(Alim)) and CodBase = @Value(CodBase)
    COMBINE_GEOM = Initiator Geometry Only
    FORMAT = MSSQL_ADO
    MSSQL_ADO_NAMED_CONNECTION = GEOPERDAS
    RESULT -> escreveSegmentoMT
escreveSegmentoMT
    CODPONACOPL2 = @Value(CodPonAcopl2)
    CODPONACOPL1 = @Value(CodPonAcopl1)
    CODFAS = @Value(CodFas)
    CODSEGMMT = @Value(CodSegmMT)
    CODCOND = @Value(CodCond)
    CODALIM = @Value(CodAlim)
    COMP_KM = @Value(Comp_km)
    -> escreveAlimDSS_2 [segmentoMT]
    -> text_line (writer TEXTLINE_10)
text_line (writer TEXTLINE_10)
    attributes: text_line_data buffer
REGULADOR: SQLExecutor
    MSSQL_ADO_QUERY_FEATURE_TYPES_FOR_MERGE_FILTERS = Yes
    MSSQL_ADO_COMMAND_TIMEOUT = 1000
    DATASET = GEOPERDAS_DAIMON2018
    COMBINE_ATTRS = Result Attributes Only
    EXPOSED_ATTRIBUTE_LIST = CodRegulMT,CodAlim,CodBnc,CodPonAcopl1,CodPonAcopl2,PotNom_kVA,TipRegul,TenRgl_pu,CodFasPrim,CodFasSecu,Resis_%,ReatHL_%,PerdTtl_W,PerdVz_W,Descr
    SQL_STATEMENT:
      select * from StoredReguladorMT
      where CodAlim in (@Value(Alim)) and CodBase = @Value(CodBase)
    COMBINE_GEOM = Initiator Geometry Only
    FORMAT = MSSQL_ADO
    MSSQL_ADO_NAMED_CONNECTION = GEOPERDAS_ANEEL_PROD
    RESULT -> escreveRegulador
escreveRegulador
    CODPONACOPL2 = @Value(CodPonAcopl2)
    TENRGL_PU = @Value(TenRgl_pu)
    CODPONACOPL1 = @Value(CodPonAcopl1)
    PERDTTL_W = @Value(PerdTtl_W)
    CODREGULMT = @Value(CodRegulMT)
    DESCR = @Value(Descr)
    CODFASPRIM = @Value(CodFasPrim)
    RESIS__ = @Value(Resis_%)
    POTNOM_KVA = @Value(PotNom_kVA)
    CODALIM = @Value(CodAlim)
    PERDVZ_W = @Value(PerdVz_W)
    REATHL__ = @Value(ReatHL_%)
    -> text_line (writer TEXTLINE_6)
    -> escreveAlimDSS_2 [RT]
text_line (writer TEXTLINE_6)
    attributes: text_line_data buffer
Chave: SQLExecutor
    MSSQL_ADO_QUERY_FEATURE_TYPES_FOR_MERGE_FILTERS = Yes
    MSSQL_ADO_COMMAND_TIMEOUT = 100
    DATASET = GEOPERDAS_DAIMON2018
    COMBINE_ATTRS = Result Attributes Only
    EXPOSED_ATTRIBUTE_LIST = CodChvMT,CodAlim,CodPonAcopl1,CodPonAcopl2,CodFas,EstChv
    SQL_STATEMENT:
      select * from StoredChaveMT
      where CodAlim in (@Value(Alim)) and CodBase = @Value(CodBase)
    COMBINE_GEOM = Initiator Geometry Only
    FORMAT = MSSQL_ADO
    MSSQL_ADO_NAMED_CONNECTION = GEOPERDAS_ANEEL_PROD
    RESULT -> escreveChavesMT
escreveChavesMT
    CODPONACOPL2 = @Value(CodPonAcopl2)
    CODPONACOPL1 = @Value(CodPonAcopl1)
    ESTCHV = @Value(EstChv)
    CODCHVMT = @Value(CodChvMT)
    CODFAS = @Value(CodFas)
    -> text_line (writer TEXTLINE_7)
    -> escreveAlimDSS_2 [chavesMT]
text_line (writer TEXTLINE_7)
    attributes: text_line_data buffer
Ramal: SQLExecutor
    MSSQL_ADO_QUERY_FEATURE_TYPES_FOR_MERGE_FILTERS = Yes
    MSSQL_ADO_COMMAND_TIMEOUT = 1000
    DATASET = GEOPERDAS_DAIMON2018
    COMBINE_ATTRS = Result Attributes Only
    EXPOSED_ATTRIBUTE_LIST = CodRmlBT,CodTrafo,CodPonAcopl1,CodPonAcopl2,CodFas,CodCond,Comp_km,CodAlim
    SQL_STATEMENT:
      select * from StoredRamalBT
      where CodAlim in (@Value(Alim)) and CodBase = @Value(CodBase)
    COMBINE_GEOM = Initiator Geometry Only
    FORMAT = MSSQL_ADO
    MSSQL_ADO_NAMED_CONNECTION = GEOPERDAS_ANEEL_PROD
    RESULT -> escreveRamalBT
escreveRamalBT
    CODPONACOPL2 = @Value(CodPonAcopl2)
    CODPONACOPL1 = @Value(CodPonAcopl1)
    CODFAS = @Value(CodFas)
    CODCOND = @Value(CodCond)
    CODALIM = @Value(CodAlim)
    COMP_KM = @Value(Comp_km)
    CODRMLBT = @Value(CodRmlBT)
    -> text_line (writer TEXTLINE_4)
    -> escreveAlimDSS_2 [ramal]
text_line (writer TEXTLINE_4)
    attributes: text_line_data buffer
Transformador: SQLExecutor
    MSSQL_ADO_QUERY_FEATURE_TYPES_FOR_MERGE_FILTERS = Yes
    MSSQL_ADO_COMMAND_TIMEOUT = 1000
    DATASET = GEOPERDAS_DAIMON2018
    COMBINE_ATTRS = Result Attributes Only
    EXPOSED_ATTRIBUTE_LIST = CodAlim,CodBnc,CodFasPrim,CodFasSecu,CodFasTerc,CodPonAcopl1,CodPonAcopl2,CodTrafo,Descr,PerdTtl_%,PerdVz_%,PotNom_kVA,Propr,ReatHL_%,ReatHT_%,ReatLT_%,Resis_%,SemCarga,Tap_pu,TenSecu_kV,TipTrafo
    SQL_STATEMENT:
      select * from StoredTrafoMTMTMTBT
      where CodAlim in (@Value(Alim)) and CodBase = @Value(CodBase)
      and tenSecu_kv not in (19.92,7.97) -- elimina posto transformador
    COMBINE_GEOM = Initiator Geometry Only
    FORMAT = MSSQL_ADO
    MSSQL_ADO_NAMED_CONNECTION = GEPERDAS_BDE_PC96
    RESULT -> escreveTrafoMTBT_DSS [AttributeCreator_3_Input]
escreveTrafoMTBT_DSS
    REATLT__ = @Value(ReatLT_%)
    CODFASPRIM = @Value(CodFasPrim)
    CODBNC = @Value(CodBnc)
    PERDTTL__ = @Value(PerdTtl_%)
    PROPR = @Value(Propr)
    TIPTRAFO = @Value(TipTrafo)
    REATHL__ = @Value(ReatHL_%)
    PERDVZ__ = @Value(PerdVz_%)
    CODALIM = @Value(CodAlim)
    SEMCARGA = @Value(SemCarga)
    TENSECU_KV = @Value(TenSecu_kV)
    RESIS__ = @Value(Resis_%)
    boolFiltraTrafoVazio = 0
    DESCR = @Value(Descr)
    CODPONACOPL2 = @Value(CodPonAcopl2)
    CODFASTERC = @Value(CodFasTerc)
    POTNOM_KVA = @Value(PotNom_kVA)
    TAP_PU = @Value(Tap_pu)
    CODPONACOPL1 = @Value(CodPonAcopl1)
    REATHT__ = @Value(ReatHT_%)
    CODFASSECU = @Value(CodFasSecu)
    CODTRAFO = @Value(CodTrafo)
    AttributeCreator_3_Output -> text_line (writer TEXTLINE_1)
    AttributeCreator_3_Output -> escreveAlimDSS_2 [trafoMTMTMTBT]
text_line (writer TEXTLINE_1)
    attributes: text_line_data buffer
PostoTransformador: SQLExecutor
    MSSQL_ADO_QUERY_FEATURE_TYPES_FOR_MERGE_FILTERS = Yes
    MSSQL_ADO_COMMAND_TIMEOUT = 1000
    DATASET = GEOPERDAS_DAIMON2018
    COMBINE_ATTRS = Result Attributes Only
    EXPOSED_ATTRIBUTE_LIST = CodTrafo,CodBnc,CodAlim,CodPonAcopl1,CodPonAcopl2,PotNom_kVA,TipTrafo,CodFasPrim,CodFasSecu,CodFasTerc,TenSecu_kV,Resis_%,ReatHL_%,ReatHT_%,ReatLT_%,PerdVz_%,PerdTtl_%,Propr,Descr
    SQL_STATEMENT:
      select * from StoredTrafoMTMTMTBT
      where CodAlim in (@Value(Alim)) and CodBase = @Value(CodBase)
      and tenSecu_kv in (19.92,7.97) -- 34.5
    COMBINE_GEOM = Initiator Geometry Only
    FORMAT = MSSQL_ADO
    MSSQL_ADO_NAMED_CONNECTION = GEOPERDAS_ANEEL_PROD
    RESULT -> escrevePT
escrevePT
    CODFASPRIM = @Value(CodFasPrim)
    CODBNC = @Value(CodBnc)
    PERDTTL__ = @Value(PerdTtl_%)
    TIPTRAFO = @Value(TipTrafo)
    REATHL__ = @Value(ReatHL_%)
    PERDVZ__ = @Value(PerdVz_%)
    CODALIM = @Value(CodAlim)
    TENSECU_KV = @Value(TenSecu_kV)
    RESIS__ = @Value(Resis_%)
    DESCR = @Value(Descr)
    CODPONACOPL2 = @Value(CodPonAcopl2)
    POTNOM_KVA = @Value(PotNom_kVA)
    CODPONACOPL1 = @Value(CodPonAcopl1)
    CODFASSECU = @Value(CodFasSecu)
    CODTRAFO = @Value(CodTrafo)
    -> escreveAlimDSS_2 [PT]
    -> text_line (writer TEXTLINE_2)
text_line (writer TEXTLINE_2)
    attributes: text_line_data buffer
Consumo_Clientes_2: SQLExecutor
    MSSQL_ADO_QUERY_FEATURE_TYPES_FOR_MERGE_FILTERS = Yes
    MSSQL_ADO_COMMAND_TIMEOUT = 1000
    DATASET = GEOPERDAS_DAIMON2018
    COMBINE_ATTRS = Result Attributes Only
    EXPOSED_ATTRIBUTE_LIST = CodAlim,CodAlimAtrib,CodBase,CodConsBT,CodFas,CodPonAcopl,CodRmlBT,CodSubAtrib,CodTrafo,CodTrafoAtrib,Descr,EnerMedid01_MWh,EnerMedid02_MWh,EnerMedid03_MWh,EnerMedid04_MWh,EnerMedid05_MWh,EnerMedid06_MWh,EnerMedid07_MWh,EnerMedid08_MWh,EnerMedid09_MWh,EnerMedid10_MWh,EnerMedid11_MWh,EnerMedid12_MWh,SemRedAssoc,TipCrvaCarga,TipMedi,TipTrafo,TnsFas_kV,TnsLnh_kV
    SQL_STATEMENT:
      select tr.TipTrafo, bt.* from StoredCargaBT as bt
      inner join StoredTrafoMTMTMTBT as tr on tr.CodTrafo = bt.codTrafo and tr.Codbase = @Value(CodBase) --corrige erro banco sujo
      where bt.CodAlim in (@Value(Alim)) and bt.CodBase = @Value(CodBase)
    COMBINE_GEOM = Initiator Geometry Only
    FORMAT = MSSQL_ADO
    MSSQL_ADO_NAMED_CONNECTION = GEOPERDAS_ANEEL_NOVO
    RESULT -> escreveCargaBTAnual [AttributeCreator_2_Input]
Note: Extrai Dados G-Dis - Clientes MT
Clientes_MT: SQLExecutor
    MSSQL_ADO_QUERY_FEATURE_TYPES_FOR_MERGE_FILTERS = Yes
    MSSQL_ADO_COMMAND_TIMEOUT = 30
    DATASET = GEOPERDAS_DAIMON2018
    COMBINE_ATTRS = Result Attributes Only
    EXPOSED_ATTRIBUTE_LIST = CodConsMT,CodAlim,CodFas,CodPonAcopl,TipCrvaCarga,EnerMedid01_MWh,EnerMedid02_MWh,EnerMedid03_MWh,EnerMedid04_MWh,EnerMedid05_MWh,EnerMedid06_MWh,EnerMedid07_MWh,EnerMedid08_MWh,EnerMedid09_MWh,EnerMedid10_MWh,EnerMedid11_MWh,EnerMedid12_MWh,Descr
    SQL_STATEMENT:
      select * from StoredCargaMT
      where CodAlim in (@Value(Alim)) and CodBase = @Value(CodBase)
    COMBINE_GEOM = Initiator Geometry Only
    FORMAT = MSSQL_ADO
    MSSQL_ADO_NAMED_CONNECTION = GEOPERDAS_ANEEL_PROD
    RESULT -> escreveCargaMTAnual
Alim_gdis_OpenDSS (writer CSV_2) [off]
    attributes: Alim char(11)
Note: Extrai PEL da cabeça do alimentador
SQLCreator_2
    MSSQL_ADO_QUERY_FEATURE_TYPES_FOR_MERGE_FILTERS = Yes
    MSSQL_ADO_COMMAND_TIMEOUT = 30
    DATASET = GEOPERDAS_DAIMON2018
    EXPOSED_ATTRIBUTE_LIST = _tensaoNom,CodAlim,CodPonAcopl
    SQL_STATEMENT:
      select CodAlim, CodPonAcopl, TenNom_kV as '_tensaoNom'
      from StoredCircMT
      where CodBase = $(CodBase)

      --Select al.PEL, al.NUMALM, al.REFSE, br.TENNOM
      --From Dgr340 as al
      --inner join DGR382 AS br on br.REFSE = al.refse  and br.REFBAR = al.REFBAR
      --order by al.refse
    FORMAT = MSSQL_ADO
    MSSQL_ADO_NAMED_CONNECTION = GEOPERDAS_ANEEL_NOVO
    RESULT -> StringReplacer
StringReplacer
    REGEXP = NO
    SRC_ATTRS = _tensaoNom
    REPLACE_TEXT = .
    FIND_TEXT = ,
    NO_MATCH = _FME_NO_OP_
    CASE = NO
    -> escreveAlimDSS_2 [cabecaAlim]
    -> verificaGDMT_Anual [getNivelTensao]
abaFME (reader XLSXR_2)
    attributes: CodAlim char(8), Simular? number(2,0), Instalacao char(11), TipoEqpto char(11), Eqpto/PntInjecao char(17), NomeUsina char(38), curvaOpenDSS char(154), Med(kWh)_Jan number(17,11), Med(kWh)_Fev number(17,11), Med(kWh)_Mar number(10,4), Med(kWh)_Abr number(18,12), Med(kWh)_Mai number(18,12), Med(kWh)_Jun number(19,12), Med(kWh)_Jul number(18,12), Med(kWh)_Ago number(18,12), Med(kWh)_Set number(18,12), Med(kWh)_Out number(10,5), Med(kWh)_Nov number(18,12), Med(kWh)_Dez number(18,12)
    -> verificaGDMT_Anual [AttributeCreator_Input]
verificaGDMT_Anual
    _TENSAONOM = @Value(_tensaoNom)
    MED_KWH__JUL = @Value(Med(kWh)_Jul)
    TIPOEQPTO = @Value(TipoEqpto)
    NOMEUSINA = @Value(NomeUsina)
    MED_KWH__ABR = @Value(Med(kWh)_Abr)
    MED_KWH__DEZ = @Value(Med(kWh)_Dez)
    MED_KWH__OUT = @Value(Med(kWh)_Out)
    MED_KWH__AGO = @Value(Med(kWh)_Ago)
    ALIM = @Value(Alim)
    CODALIM = @Value(CodAlim)
    MED_KWH__JAN = @Value(Med(kWh)_Jan)
    MED_KWH__SET = @Value(Med(kWh)_Set)
    MED_KWH__FEV = @Value(Med(kWh)_Fev)
    MED_KWH__NOV = @Value(Med(kWh)_Nov)
    MED_KWH__JUN = @Value(Med(kWh)_Jun)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    verificaGDMT_Output_1 -> text_line (writer TEXTLINE_36)
    verificaGDMT_Output_2 -> text_line (writer TEXTLINE_37)
    verificaGDMT_Output_3 -> text_line (writer TEXTLINE_38)
    verificaGDMT_Output_4 -> text_line (writer TEXTLINE_39)
    verificaGDMT_Output_5 -> text_line (writer TEXTLINE_40)
    verificaGDMT_Output_6 -> text_line (writer TEXTLINE_41)
    verificaGDMT_Output_7 -> text_line (writer TEXTLINE_42)
    verificaGDMT_Output_8 -> text_line (writer TEXTLINE_43)
    verificaGDMT_Output_9 -> text_line (writer TEXTLINE_44)
    verificaGDMT_Output_10 -> text_line (writer TEXTLINE_45)
    verificaGDMT_Output_11 -> text_line (writer TEXTLINE_46)
    verificaGDMT_Output_12 -> text_line (writer TEXTLINE_47)
text_line (writer TEXTLINE_36)
    attributes: text_line_data buffer
text_line (writer TEXTLINE_37)
    attributes: text_line_data buffer
text_line (writer TEXTLINE_38)
    attributes: text_line_data buffer
text_line (writer TEXTLINE_39)
    attributes: text_line_data buffer
text_line (writer TEXTLINE_40)
    attributes: text_line_data buffer
text_line (writer TEXTLINE_41)
    attributes: text_line_data buffer
text_line (writer TEXTLINE_42)
    attributes: text_line_data buffer
text_line (writer TEXTLINE_43)
    attributes: text_line_data buffer
text_line (writer TEXTLINE_44)
    attributes: text_line_data buffer
text_line (writer TEXTLINE_45)
    attributes: text_line_data buffer
text_line (writer TEXTLINE_46)
    attributes: text_line_data buffer
text_line (writer TEXTLINE_47)
    attributes: text_line_data buffer
fatork_cemig (reader XLSXR_1)
    attributes: CodCrvCrg char(5), DU number(18,14), SA number(18,14), DO number(18,14), E string
    -> escreveCargaBTAnual [escreveCargaBT_CurvasDeCarga_1]
    -> escreveCargaMTAnual [CurvasCarga]
escreveCargaBTAnual
    ENERMEDID07_MWH = @Value(EnerMedid07_MWh)
    ENERMEDID10_MWH = @Value(EnerMedid10_MWh)
    DO = @Value(DO)
    TIPTRAFO = @Value(TipTrafo)
    CODCONSBT = @Value(CodConsBT)
    SA = @Value(SA)
    ENERMEDID04_MWH = @Value(EnerMedid04_MWh)
    ENERMEDID09_MWH = @Value(EnerMedid09_MWh)
    ENERMEDID02_MWH = @Value(EnerMedid02_MWh)
    CODALIM = @Value(CodAlim)
    TIPCRVACARGA = @Value(TipCrvaCarga)
    ENERMEDID06_MWH = @Value(EnerMedid06_MWh)
    Mes = 1
    ENERMEDID08_MWH = @Value(EnerMedid08_MWh)
    CODFAS = @Value(CodFas)
    ENERMEDID05_MWH = @Value(EnerMedid05_MWh)
    CODPONACOPL = @Value(CodPonAcopl)
    ENERMEDID03_MWH = @Value(EnerMedid03_MWh)
    CODCRVCRG = @Value(CodCrvCrg)
    ENERMEDID11_MWH = @Value(EnerMedid11_MWh)
    ENERMEDID01_MWH = @Value(EnerMedid01_MWh)
    ENERMEDID12_MWH = @Value(EnerMedid12_MWh)
    DU = @Value(DU)
    CODTRAFO = @Value(CodTrafo)
    1 -> text_line (writer TEXTLINE_11)
    1 -> escreveAlimDSS_2 [cargaBT]
    2 -> text_line (writer TEXTLINE_12)
    3 -> text_line (writer TEXTLINE_13)
    4 -> text_line (writer TEXTLINE_14)
    5 -> text_line (writer TEXTLINE_15)
    6 -> text_line (writer TEXTLINE_16)
    7 -> text_line (writer TEXTLINE_17)
    8 -> text_line (writer TEXTLINE_18)
    9 -> text_line (writer TEXTLINE_19)
    10 -> text_line (writer TEXTLINE_20)
    11 -> text_line (writer TEXTLINE_21)
    12 -> text_line (writer TEXTLINE_22)
text_line (writer TEXTLINE_11)
    attributes: text_line_data buffer
text_line (writer TEXTLINE_12)
    attributes: text_line_data buffer
text_line (writer TEXTLINE_13)
    attributes: text_line_data buffer
text_line (writer TEXTLINE_14)
    attributes: text_line_data buffer
text_line (writer TEXTLINE_15)
    attributes: text_line_data buffer
text_line (writer TEXTLINE_16)
    attributes: text_line_data buffer
text_line (writer TEXTLINE_17)
    attributes: text_line_data buffer
text_line (writer TEXTLINE_18)
    attributes: text_line_data buffer
text_line (writer TEXTLINE_19)
    attributes: text_line_data buffer
text_line (writer TEXTLINE_20)
    attributes: text_line_data buffer
text_line (writer TEXTLINE_21)
    attributes: text_line_data buffer
text_line (writer TEXTLINE_22)
    attributes: text_line_data buffer
escreveCargaMTAnual
    ENERMEDID07_MWH = @Value(EnerMedid07_MWh)
    ENERMEDID10_MWH = @Value(EnerMedid10_MWh)
    DO = @Value(DO)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    CODALIM = @Value(CodAlim)
    E = @Value(E)
    ENERMEDID06_MWH = @Value(EnerMedid06_MWh)
    TIPCRVACARGA = @Value(TipCrvaCarga)
    Mes = 1
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    1 -> text_line (writer TEXTLINE_5)
    1 -> escreveAlimDSS_2 [cargaMT]
    1_2 -> text_line (writer TEXTLINE_23)
    1_3 -> text_line (writer TEXTLINE_24)
    1_4 -> text_line (writer TEXTLINE_25)
    1_5 -> text_line (writer TEXTLINE_26)
    1_6 -> text_line (writer TEXTLINE_27)
    1_7 -> text_line (writer TEXTLINE_29)
    1_8 -> text_line (writer TEXTLINE_30)
    1_9 -> text_line (writer TEXTLINE_31)
    1_10 -> text_line (writer TEXTLINE_32)
    1_11 -> text_line (writer TEXTLINE_33)
    1_12 -> text_line (writer TEXTLINE_28)
escreveAlimDSS_2
    CODPONACOPL = @Value(CodPonAcopl)
    CODPONACOPL1 = @Value(CodPonAcopl1)
    CODSEGMMT = @Value(CodSegmMT)
    CODALIM = @Value(CodAlim)
    TEXT_LINE_DATA = @Value(text_line_data)
    _TENSAONOM = @Value(_tensaoNom)
    ALIM = @Value(Alim)
    cabeçalho1 -> text_line (writer TEXTLINE_9)
    -> text_line (writer TEXTLINE_8)
    AnualA -> text_line (writer TEXTLINE_34)
    AnualB -> text_line (writer TEXTLINE_35)
text_line (writer TEXTLINE_9)
    attributes: text_line_data buffer
text_line (writer TEXTLINE_8)
    attributes: text_line_data buffer
text_line (writer TEXTLINE_34)
    attributes: text_line_data buffer
text_line (writer TEXTLINE_35)
    attributes: text_line_data buffer
text_line (writer TEXTLINE_5)
    attributes: text_line_data buffer
text_line (writer TEXTLINE_23)
    attributes: text_line_data buffer
text_line (writer TEXTLINE_24)
    attributes: text_line_data buffer
text_line (writer TEXTLINE_25)
    attributes: text_line_data buffer
text_line (writer TEXTLINE_26)
    attributes: text_line_data buffer
text_line (writer TEXTLINE_27)
    attributes: text_line_data buffer
text_line (writer TEXTLINE_29)
    attributes: text_line_data buffer
text_line (writer TEXTLINE_30)
    attributes: text_line_data buffer
text_line (writer TEXTLINE_31)
    attributes: text_line_data buffer
text_line (writer TEXTLINE_32)
    attributes: text_line_data buffer
text_line (writer TEXTLINE_33)
    attributes: text_line_data buffer
text_line (writer TEXTLINE_28)
    attributes: text_line_data buffer

FME custom transformer escreveChavesMT

Parameters:
- CODFAS = @Value(CodFas)   # CodFas
- CODPONACOPL1 = @Value(CodPonAcopl1)   # CodPonAcopl1
- CODPONACOPL2 = @Value(CodPonAcopl2)   # CodPonAcopl2
- CODCHVMT = @Value(CodChvMT)   # CodChvMT
- ESTCHV = @Value(EstChv)   # EstChv

Input (input)
    -> AttributeValueMapper_3
Note: barrasDSS
AttributeValueMapper_3
    LUT = AN,.1.0,BN,.1.0,CN,.1.0,ABN,.1.2.0,BCN,.1.2.0,CAN,.1.2.0,ABCN,.1.2.3.0
    DIRECTION = Forward (Source To Destination)
    SRC = CodFas
    VAL_ATTR = _barrasDSS
    -> AttributeValueMapper_4
Note: fasesDSS
AttributeValueMapper_4
    LUT = A,1,B,1,C,1,AB,2,BC,2,CA,2,ABC,3,AN,1,BN,1,CN,1,ABN,2,BCN,2,CAN,2,ABCN,3
    DIRECTION = Forward (Source To Destination)
    SRC = CodFas
    VAL_ATTR = _fasesDSS
    -> Tester_2
Note: modela somente chaves fechadas
Tester_2
    TEST_DESCRIPTION = ""
    TEST_MODE = Automatic
    TEST_CLAUSE = TEST @Value(EstChv) = 2
    BOOL_OP = OR
    PASSED -> AttributeCreator_2
    FAILED -> AttributeCreator_3
Note: linha
AttributeCreator_2
    ATTR_TABLE = SET_TO text_line_data = new line.@Value(CodChvMT) bus1=@Value(CodPonAcopl1)@Value(_barrasDSS),bus2=@Value(CodPonAcopl2)@Value(_barrasDSS),Phases=@Value(_fasesDSS),r1=0.001,r0=0.001,x1=0,x0=0,c1=0,c0=0,Length=0.001,Units=km,switch=T
    -> AttributeRemover
Note: OBS: nao é possivel modelar a chave fechada. / adicionar este bloco, fecha-se o alimentador em paralelo
AttributeCreator_3
    ATTR_TABLE:
      SET_TO text_line_data = new line.@Value(CodChvMT) bus1=@Value(CodPonAcopl1)@Value(_barrasDSS),bus2=@Value(CodPonAcopl2)@Value(_barrasDSS),Phases=@Value(_fasesDSS),r1=0.001,r0=0.001,x1=0,x0=0,c1=0,c0=0,Length=0.001,Units=km,switch=T
        open line.@Value(CodChvMT) term=1
    -> AttributeRemover
AttributeRemover
    REMOVE_ATTRS = _fasesDSS,CodPonAcopl1,_barrasDSS,CodFas,CodPonAcopl2,CodChvMT
    -> Output (output)
Output (output)

FME custom transformer criaStringVoltageBases

Parameters:
- ALIM = @Value(Alim)   # Alim

temPT (input)
    -> AttributeCreator_14
Note: cria string com tensões base
AttributeCreator_14
    ATTR_TABLE = SET_TO _tensaoNom = 34.5 13.8
    -> AttributeCreator_11
naoTemPT (input)
    -> AttributeCreator_16
AttributeCreator_16
    ATTR_TABLE = SET_TO _tensaoNom = @Value(_tensaoNom)
    -> AttributeCreator_11
Note: string VoltageBases
AttributeCreator_11
    ATTR_TABLE:
      SET_TO linha3_2 = ! Seta as tensoes de base do sistema
        Set voltagebases="@Value(_tensaoNom) 0.24 0.22"

        ! Calcula as tensoes das linhas em pu
        CalcVoltageBases

        ! Solve
    -> AttributeRemover
AttributeRemover
    REMOVE_ATTRS = TENNOM,MÉDIA,_tensaoNom,Eqpto/Pnt Injecao,Nome Usina,Código OpendDSS2,CodPonAcopl1
    -> Output (output)
Output (output)

FME custom transformer escreveCargaBTAnual

Parameters:
- Mes = 1
- CODCONSBT = @Value(CodConsBT)   # CodConsBT
- ENERMEDID10_MWH = @Value(EnerMedid10_MWh)   # Enermedid10 Mwh
- ENERMEDID07_MWH = @Value(EnerMedid07_MWh)   # Enermedid07 Mwh
- DO = @Value(DO)
- TIPTRAFO = @Value(TipTrafo)   # TipTrafo
- TIPCRVACARGA = @Value(TipCrvaCarga)   # TipCrvaCarga
- ENERMEDID02_MWH = @Value(EnerMedid02_MWh)   # Enermedid02 Mwh
- CODALIM = @Value(CodAlim)   # CodAlim
- ENERMEDID11_MWH = @Value(EnerMedid11_MWh)   # Enermedid11 Mwh
- ENERMEDID09_MWH = @Value(EnerMedid09_MWh)   # Enermedid09 Mwh
- ENERMEDID01_MWH = @Value(EnerMedid01_MWh)   # Enermedid01 Mwh
- SA = @Value(SA)
- CODFAS = @Value(CodFas)   # CodFas
- ENERMEDID03_MWH = @Value(EnerMedid03_MWh)   # Enermedid03 Mwh
- CODTRAFO = @Value(CodTrafo)   # CodTrafo
- ENERMEDID04_MWH = @Value(EnerMedid04_MWh)   # Enermedid04 Mwh
- ENERMEDID05_MWH = @Value(EnerMedid05_MWh)   # Enermedid05 Mwh
- ENERMEDID12_MWH = @Value(EnerMedid12_MWh)   # Enermedid12 Mwh
- CODCRVCRG = @Value(CodCrvCrg)   # CodCrvCrg
- CODPONACOPL = @Value(CodPonAcopl)   # CodPonAcopl
- ENERMEDID08_MWH = @Value(EnerMedid08_MWh)   # Enermedid08 Mwh
- DU = @Value(DU)
- ENERMEDID06_MWH = @Value(EnerMedid06_MWh)   # Enermedid06 Mwh

escreveCargaBT_CurvasDeCarga_1 (input)
    -> escreveCargaBT [CurvasDeCarga]
    -> escreveCargaBT_2 [CurvasDeCarga]
    -> escreveCargaBT_3 [CurvasDeCarga]
    -> escreveCargaBT_4 [CurvasDeCarga]
    -> escreveCargaBT_5 [CurvasDeCarga]
    -> escreveCargaBT_6 [CurvasDeCarga]
    -> escreveCargaBT_7 [CurvasDeCarga]
    -> escreveCargaBT_8 [CurvasDeCarga]
    -> escreveCargaBT_9 [CurvasDeCarga]
    -> escreveCargaBT_10 [CurvasDeCarga]
    -> escreveCargaBT_11 [CurvasDeCarga]
    -> escreveCargaBT_12 [CurvasDeCarga]
AttributeCreator_2_Input (input)
    -> AttributeCreator_2
    -> AttributeCreator_3
    -> AttributeCreator_4
    -> AttributeCreator_5
    -> AttributeCreator_6
    -> AttributeCreator_7
    -> AttributeCreator_8
    -> AttributeCreator_9
    -> AttributeCreator_10
    -> AttributeCreator_11
    -> AttributeCreator
    -> AttributeCreator_12
Note: mês a calcular
AttributeCreator_2
    ATTR_TABLE = SET_TO mesACalcular = 1
    -> escreveCargaBT
escreveCargaBT
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 1 (output)
1 (output)
Note: mês a calcular
AttributeCreator_3
    ATTR_TABLE = SET_TO mesACalcular = 2
    -> escreveCargaBT_2
escreveCargaBT_2
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 2 (output)
2 (output)
Note: mês a calcular
AttributeCreator_4
    ATTR_TABLE = SET_TO mesACalcular = 3
    -> escreveCargaBT_3
escreveCargaBT_3
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 3 (output)
3 (output)
Note: mês a calcular
AttributeCreator_5
    ATTR_TABLE = SET_TO mesACalcular = 4
    -> escreveCargaBT_4
escreveCargaBT_4
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 4 (output)
4 (output)
Note: mês a calcular
AttributeCreator_6
    ATTR_TABLE = SET_TO mesACalcular = 5
    -> escreveCargaBT_5
escreveCargaBT_5
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 5 (output)
5 (output)
Note: mês a calcular
AttributeCreator_7
    ATTR_TABLE = SET_TO mesACalcular = 6
    -> escreveCargaBT_6
escreveCargaBT_6
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 6 (output)
6 (output)
Note: mês a calcular
AttributeCreator_8
    ATTR_TABLE = SET_TO mesACalcular = 7
    -> escreveCargaBT_7
escreveCargaBT_7
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 7 (output)
7 (output)
Note: mês a calcular
AttributeCreator_9
    ATTR_TABLE = SET_TO mesACalcular = 8
    -> escreveCargaBT_8
escreveCargaBT_8
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 8 (output)
8 (output)
Note: mês a calcular
AttributeCreator_10
    ATTR_TABLE = SET_TO mesACalcular = 9
    -> escreveCargaBT_9
escreveCargaBT_9
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 9 (output)
9 (output)
Note: mês a calcular
AttributeCreator_11
    ATTR_TABLE = SET_TO mesACalcular = 10
    -> escreveCargaBT_10
escreveCargaBT_10
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 10 (output)
10 (output)
Note: mês a calcular
AttributeCreator
    ATTR_TABLE = SET_TO mesACalcular = 11
    -> escreveCargaBT_11
escreveCargaBT_11
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 11 (output)
11 (output)
Note: mês a calcular
AttributeCreator_12
    ATTR_TABLE = SET_TO mesACalcular = 12
    -> escreveCargaBT_12
escreveCargaBT_12
    ENERMEDID07_MWH = @Value(EnerMedid07_MWh)
    ENERMEDID10_MWH = @Value(EnerMedid10_MWh)
    DO = @Value(DO)
    CODCONSBT = @Value(CodConsBT)
    SA = @Value(SA)
    TIPTRAFO = @Value(TipTrafo)
    ENERMEDID04_MWH = @Value(EnerMedid04_MWh)
    ENERMEDID09_MWH = @Value(EnerMedid09_MWh)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    CODPONACOPL = @Value(CodPonAcopl)
    CODCRVCRG = @Value(CodCrvCrg)
    ENERMEDID03_MWH = @Value(EnerMedid03_MWh)
    ENERMEDID11_MWH = @Value(EnerMedid11_MWh)
    ENERMEDID01_MWH = @Value(EnerMedid01_MWh)
    DU = @Value(DU)
    ENERMEDID12_MWH = @Value(EnerMedid12_MWh)
    CODTRAFO = @Value(CodTrafo)
    -> 12 (output)
12 (output)

FME custom transformer escreveSegmentoMT

Parameters:
- CODFAS = @Value(CodFas)   # CodFas
- CODCOND = @Value(CodCond)   # CodCond
- CODPONACOPL1 = @Value(CodPonAcopl1)   # CodPonAcopl1
- CODPONACOPL2 = @Value(CodPonAcopl2)   # CodPonAcopl2
- CODSEGMMT = @Value(CodSegmMT)   # CodSegmMT
- COMP_KM = @Value(Comp_km)   # Comp Km
- CODALIM = @Value(CodAlim)   # CodAlim

Input (input)
    -> AttributeValueMapper
Note: barrasDSS
AttributeValueMapper
    LUT = A,.1.0,B,.1.0,C,.1.0,AB,.1.2.0,BC,.1.2.0,CA,.1.2.0,ABC,.1.2.3.0
    DIRECTION = Forward (Source To Destination)
    SRC = CodFas
    VAL_ATTR = _barrasDSS
    -> AttributeValueMapper_2
Note: fasesDSS
AttributeValueMapper_2
    LUT = A,1,B,1,C,1,AB,2,BC,2,CA,2,ABC,3
    DIRECTION = Forward (Source To Destination)
    SRC = CodFas
    VAL_ATTR = _fasesDSS
    -> StringReplacer
StringReplacer
    REGEXP = NO
    SRC_ATTRS = Comp_km
    REPLACE_TEXT = .
    FIND_TEXT = ,
    NO_MATCH = _FME_NO_OP_
    CASE = NO
    -> AttributeCreator
Note: linha DSS
AttributeCreator
    ATTR_TABLE = SET_TO text_line_data = new line.@Value(CodSegmMT) bus1=@Value(CodPonAcopl1)@Value(_barrasDSS),bus2=@Value(CodPonAcopl2)@Value(_barrasDSS),Phases=@Value(_fasesDSS),Linecode=@Value(CodCond),Length=@Value(Comp_km),Units=km
    -> AttributeRemover
AttributeRemover
    REMOVE_ATTRS = CodCond,CodPonAcopl2,Comp_km,_barrasDSS,CodFas,_fasesDSS
    -> Output (output)
Output (output)

FME custom transformer escreveAlimDSSMensal

Parameters:
- CODSEGMMT = @Value(CodSegmMT)   # CodSegmMT
- CODALIM = @Value(CodAlim)   # CodAlim
- TEXT_LINE_DATA = @Value(text_line_data)   # Text Line Data
- CODPONACOPL1 = @Value(CodPonAcopl1)   # CodPonAcopl1
- ALIM = @Value(Alim)   # Alim
- _TENSAONOM = @Value(_tensaoNom)   # Tensaonom
- CODPONACOPL = @Value(CodPonAcopl)   # CodPonAcopl

CabecaAlim (input)
    -> FeatureMerger [REQUESTOR]
StringReplacer_4_Input (input)
    -> StringReplacer_4
Note: RETIRA ' ALIMENTADOR
StringReplacer_4
    REGEXP = no
    SRC_ATTRS = Alim
    FIND_TEXT = '
    NO_MATCH = _FME_NO_OP_
    CASE = no
    -> StringReplacer_3
Note: RETIRA ESPAÇO ALIMENTADOR
StringReplacer_3
    REGEXP = no
    SRC_ATTRS = Alim
    FIND_TEXT = " "
    NO_MATCH = _FME_NO_OP_
    CASE = no
    -> FeatureMerger [SUPPLIER]
    -> FeatureMerger_5 [REQUESTOR]
    -> FeatureMerger_6 [REQUESTOR]
    -> FeatureMerger_7 [REQUESTOR]
    -> FeatureMerger_8 [REQUESTOR]
    -> FeatureMerger_9 [REQUESTOR]
    -> FeatureMerger_10 [REQUESTOR]
    -> FeatureMerger_11 [REQUESTOR]
    -> FeatureMerger_12 [REQUESTOR]
    -> FeatureMerger_13 [REQUESTOR]
FeatureMerger
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(CodAlim) @Value(Alim) AUTO
    MERGED -> FeatureMerger_2 [REQUESTOR]
    MERGED -> AttributeCreator
Note: cria linha1 e arquivo de cabeçalho1
AttributeCreator
    ATTR_TABLE:
      SET_TO linha1 = ! clear

        ! new circuit.alim@Value(CodAlim) bus1=@Value(CodPonAcopl),basekv=@Value(_tensaoNom),pu=1.036

        ! Arquivo de curvas de carga normalizadas
        ! Redirect "I:\SA\GRMP\PERDAS-TECNICAS\0perdasTecnicasOpenDSS\Recursos\CurvasTxt\CurvasDeCargaDU.dss"

        ! Arquivo de condutores
        Redirect "I:\SA\GRMP\PERDAS-TECNICAS\0perdasTecnicasOpenDSS\Recursos\Condutores.dss"


      SET_TO text_line_data = ! manter este comentario para compatibilidade do C#
        new circuit.alim@Value(CodAlim) bus1=@Value(CodPonAcopl),basekv=@Value(_tensaoNom),pu=
    -> AttributeRemover_3
AttributeRemover_3
    REMOVE_ATTRS = NUMALM,REFSE,CodPonAcopl1,CodPonPEL,CodSegmMT,PEL
    -> FeatureMerger_3 [REQUESTOR]
    -> Cabecalho (output)
Cabecalho (output)
SegmentoMT (input)
    -> FeatureMerger_2 [SUPPLIER]
    -> FeatureMerger_5 [SUPPLIER]
Note: obtem trecho p/ instalacao energymeter
FeatureMerger_2
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(CodPonAcopl) @Value(CodPonAcopl1) AUTO
    MERGED -> AttributeCreator_15
Note: energy meter
AttributeCreator_15
    ATTR_TABLE:
      SET_TO linha3 =
        new energymeter.carga element=line.@Value(CodSegmMT),terminal=1
    -> FeatureMerger_14 [REQUESTOR]
FeatureMerger_5
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_3
AttributeCreator_3
    ATTR_TABLE = SET_TO linha2 = Redirect @Value(CodAlim)SegmentosMT.dss
    -> Aggregator
FeatureMerger_13_Supplier (input)
    -> FeatureMerger_13 [SUPPLIER]
FeatureMerger_13
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_12
    MERGED -> criaStringVoltageBases [temPT]
    NOT_MERGED -> criaStringVoltageBases [naoTemPT]
Note: criaStringVoltageBases
criaStringVoltageBases
    ALIM = @Value(Alim)
    -> FeatureMerger_14 [SUPPLIER]
Note: NergyMeter+CalcVoltagesBAse
FeatureMerger_14
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(Alim) AUTO
    MERGED -> StringConcatenator_3
StringConcatenator_3
    ACTION = Create New Attribute
    PARM_LINE = @Value(linha3)@Value(linha3_2)
    VAL_ATTR = linha3
    -> AttributeRemover
AttributeRemover
    REMOVE_ATTRS = CodPonAcopl,NUMALM,REFSE,linha3_2,CodPonPEL,TENNOM,PEL,MÉDIA,Eqpto/Pnt Injecao,Nome Usina,text_line_data,CodPonAcopl1,CodSegmMT,Código OpendDSS2
    -> FeatureMerger_4 [SUPPLIER]
AttributeCreator_12
    ATTR_TABLE = SET_TO linha2 = Redirect @Value(CodAlim)PT.dss
    -> Aggregator
SegmentoBT (input)
    -> FeatureMerger_6 [SUPPLIER]
FeatureMerger_6
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_2
AttributeCreator_2
    ATTR_TABLE = SET_TO linha2 = Redirect @Value(CodAlim)SegmentosBT.dss
    -> Aggregator
ReguladorMT (input)
    -> FeatureMerger_7 [SUPPLIER]
FeatureMerger_7
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_4
AttributeCreator_4
    ATTR_TABLE = SET_TO linha2 = Redirect @Value(CodAlim)Reguladores.dss
    -> Aggregator
Ramal (input)
    -> FeatureMerger_8 [SUPPLIER]
FeatureMerger_8
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_5
AttributeCreator_5
    ATTR_TABLE = SET_TO linha2 = Redirect @Value(CodAlim)Ramais.dss
    -> Aggregator
TrafoMTMTMTBT (input)
    -> FeatureMerger_9 [SUPPLIER]
FeatureMerger_9
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_6
AttributeCreator_6
    ATTR_TABLE = SET_TO linha2 = Redirect @Value(CodAlim)Transformadores.dss
    -> Aggregator
CargaBT (input)
    -> FeatureMerger_10 [SUPPLIER]
FeatureMerger_10
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_7
AttributeCreator_7
    ATTR_TABLE = SET_TO linha2 = Redirect @Value(CodAlim)CargaBT.dss
    -> Aggregator
CargaMT (input)
    -> FeatureMerger_11 [SUPPLIER]
FeatureMerger_11
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_8
AttributeCreator_8
    ATTR_TABLE = SET_TO linha2 = Redirect @Value(CodAlim)CargaMT.dss
    -> Aggregator
ChavesMT (input)
    -> FeatureMerger_12 [SUPPLIER]
FeatureMerger_12
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_9
AttributeCreator_9
    ATTR_TABLE = SET_TO linha2 = Redirect @Value(CodAlim)ChavesMT.dss
    -> Aggregator
Aggregator
    MODE = Geometry - Assemble One Level
    CONCAT_ATTRS = linha2
    AGGREGATE_TYPE = Homogeneous Collection (If Possible)
    ACCUM_ATTRS_NAME = Get Attributes From One Representative Feature
    GROUP_BY = CodAlim
    ORDERED = No
    AGGREGATE -> AttributeRemover_2
AttributeRemover_2
    REMOVE_ATTRS = CodPonAcopl1,CodSegmMT,_count
    -> FeatureMerger_3 [SUPPLIER]
FeatureMerger_3
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> StringConcatenator
StringConcatenator
    ACTION = Create New Attribute
    PARM_LINE = @Value(linha1)@Value(linha2)
    VAL_ATTR = linha1
    -> FeatureMerger_4 [REQUESTOR]
FeatureMerger_4
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(CodAlim) @Value(CodAlim) AUTO
    MERGED -> StringConcatenator_2
Note: text_line_data
StringConcatenator_2
    ACTION = Create New Attribute
    PARM_LINE = @Value(linha1)@Value(linha3)
    VAL_ATTR = text_line_data
    -> ArquivoB (output)
ArquivoB (output)

FME custom transformer escreveRegulador

Parameters:
- CODFASPRIM = @Value(CodFasPrim)   # CodFasPrim
- CODPONACOPL1 = @Value(CodPonAcopl1)   # CodPonAcopl1
- CODPONACOPL2 = @Value(CodPonAcopl2)   # CodPonAcopl2
- CODREGULMT = @Value(CodRegulMT)   # CodRegulMT
- POTNOM_KVA = @Value(PotNom_kVA)   # Potnom Kva
- REATHL__ = @Value(ReatHL_%)   # Reathl %
- RESIS__ = @Value(Resis_%)   # Resis %
- TENRGL_PU = @Value(TenRgl_pu)   # Tenrgl Pu
- CODALIM = @Value(CodAlim)   # CodAlim
- PERDTTL_W = @Value(PerdTtl_W)   # Perdttl W
- PERDVZ_W = @Value(PerdVz_W)   # Perdvz W
- DESCR = @Value(Descr)   # Descr

Input (input)
    -> AttributeRenamer
Note: tensao FN armazenada na DESCR
AttributeRenamer
    ATTR_TABLE = RENAME_SET_DEFAULT Descr > vAltaFN
    -> StringFormatter
Note: formata string vAltaFN / com 2 casas decimais
StringFormatter
    SRC_ATTRS = vAltaFN
    FORMAT = .2f
    -> Tester
Note: Se tensao FN não existe
Tester
    TEST_DESCRIPTION = ""
    TEST_MODE = Automatic
    TEST_CLAUSE:
      TEST vAltaFN ATTRIBUTE_VALUE_NULL ""
      TEST vAltaFN ATTRIBUTE_IS_EMPTY ""
      TEST vAltaFN ATTRIBUTE_IS_MISSING ""
      TEST @Value(vAltaFN) NOT_TYPE DOUBLE
    BOOL_OP = OR
    PASSED -> AttributeCreator_4
    FAILED -> AttributeFilter
    FAILED -> Inspector
AttributeCreator_4
    ATTR_TABLE = SET_TO vAltaFN = 7.97
    -> AttributeFilter
Note: TODO
AttributeFilter
    ATTR_VALUES = <EMPTY>,<MISSING>,<NULL>,<UNFILTERED>,7.97,12.70,12.90,19.92,13.80
    ATTR_NAME = vAltaFN
    7.97 -> AttributeCreator_3
    12.70 -> AttributeCreator_5
    12.90 -> AttributeCreator_5
    19.92 -> AttributeCreator_6
    13.80 -> AttributeCreator_3
Note: seta PT ratio RTs
AttributeCreator_3
    ATTR_TABLE = SET_TO _ptRatio = 66.4
    -> AttributeValueMapper
AttributeCreator_5
    ATTR_TABLE = SET_TO _ptRatio = 105.8
    -> AttributeValueMapper
AttributeCreator_6
    ATTR_TABLE = SET_TO _ptRatio = 166
    -> AttributeValueMapper
Note: barrasDSS / OBS: necessario tratar A,B e C para / RTs monofasicos
AttributeValueMapper
    LUT = AN,.1.0,BN,.2.0,CN,.3.0,A,.1.0,B,.2.0,C,.3.0,ABC,.1.2.3.0
    DIRECTION = Forward (Source To Destination)
    SRC = CodFasPrim
    VAL_ATTR = _barrasDSS
    -> AttributeValueMapper_2
Note: fasesDSS
AttributeValueMapper_2
    LUT = AN,1,BN,1,CN,1,A,1,B,1,C,1,ABC,3
    DIRECTION = Forward (Source To Destination)
    SRC = CodFasPrim
    VAL_ATTR = _fasesDSS
    -> StringReplacer
Note: Corrige KVAS, XHL, loadloss, TapPU
StringReplacer
    REGEXP = NO
    SRC_ATTRS = PotNom_kVA,TenRgl_pu,ReatHL_%,Resis_%
    REPLACE_TEXT = .
    FIND_TEXT = ,
    NO_MATCH = _FME_NO_OP_
    CASE = NO
    -> AttributeCreator_2
Note: variaveis de perdas RT. / Divide perda em Watts por 1000 e / depois multiplca por 100%
AttributeCreator_2
    ATTR_TABLE:
      SET_TO noloadLoss = @div( @mult( @Value(PerdVz_W),0.1 ), @Value(PotNom_kVA) )
      SET_TO loadLoss = @div( @mult( @Value(PerdTtl_W),0.1 ), @Value(PotNom_kVA) )
    -> AttributeCreator_7
Note: subtrai perdas totais das a vazio
AttributeCreator_7
    ATTR_TABLE = SET_TO loadLoss = @sub(@Value(loadLoss),@Value(noloadLoss))
    -> AttributeCreator
Note: linha RT
AttributeCreator
    ATTR_TABLE:
      SET_TO text_line_data = new transformer.T@Value(CodRegulMT)@Value(CodFasPrim) Phases=@Value(_fasesDSS),windings=2,buses=(@Value(CodPonAcopl1)@Value(_barrasDSS),@Value(CodPonAcopl2)@Value(_barrasDSS)),conns=(LN,LN),kvs=(@Value(vAltaFN) @Value(vAltaFN)),kvas=(@Value(PotNom_kVA),@Value(PotNom_kVA)),xhl=@Value(ReatHL_%),%loadloss=@Value(loadLoss),%noloadloss=@Value(noloadLoss)
        new RegControl.R@Value(CodRegulMT)@Value(CodFasPrim) transformer=T@Value(CodRegulMT)@Value(CodFasPrim),winding=2,PTphase=1,ptratio=@Value(_ptRatio),band=3,vreg=125
    -> AttributeRemover
AttributeRemover
    REMOVE_ATTRS = CodPonAcopl2,CodRegulMT,_fasesDSS,CodPonAcopl1,PerdVz_W,_ptRatio,loadLoss,CodFasPrim,_barrasDSS,noloadLoss,vAltaFN,PerdTtl_W,PotNom_kVA,Resis_%,TenRgl_pu,ReatHL_%
    -> Output (output)
Output (output)
Inspector

FME custom transformer escreveAlimDSSAnual

Parameters:
- CODSEGMMT = @Value(CodSegmMT)   # CodSegmMT
- CODALIM = @Value(CodAlim)   # CodAlim
- TEXT_LINE_DATA = @Value(text_line_data)   # Text Line Data
- CODPONACOPL1 = @Value(CodPonAcopl1)   # CodPonAcopl1
- ALIM = @Value(Alim)   # Alim
- _TENSAONOM = @Value(_tensaoNom)   # Tensaonom
- CODPONACOPL = @Value(CodPonAcopl)   # CodPonAcopl

CabecaAlim (input)
    -> FeatureMerger [REQUESTOR]
StringReplacer_4_Input (input)
    -> StringReplacer_4
Note: RETIRA ' ALIMENTADOR
StringReplacer_4
    REGEXP = no
    SRC_ATTRS = Alim
    FIND_TEXT = '
    NO_MATCH = _FME_NO_OP_
    CASE = no
    -> StringReplacer_3
Note: RETIRA ESPAÇO ALIMENTADOR
StringReplacer_3
    REGEXP = no
    SRC_ATTRS = Alim
    FIND_TEXT = " "
    NO_MATCH = _FME_NO_OP_
    CASE = no
    -> FeatureMerger [SUPPLIER]
    -> FeatureMerger_5 [REQUESTOR]
    -> FeatureMerger_6 [REQUESTOR]
    -> FeatureMerger_7 [REQUESTOR]
    -> FeatureMerger_8 [REQUESTOR]
    -> FeatureMerger_9 [REQUESTOR]
    -> FeatureMerger_12 [REQUESTOR]
    -> FeatureMerger_13 [REQUESTOR]
FeatureMerger
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(CodAlim) @Value(Alim) AUTO
    MERGED -> FeatureMerger_2 [REQUESTOR]
    MERGED -> AttributeCreator
Note: cria linha1 e arquivo de cabeçalho1
AttributeCreator
    ATTR_TABLE:
      SET_TO linha1 = ! clear

        ! new circuit.alim@Value(CodAlim) bus1=@Value(CodPonAcopl),basekv=@Value(_tensaoNom),pu=1.036

        ! Arquivo de curvas de carga normalizadas
        ! Redirect "I:\SA\GRMP\PERDAS-TECNICAS\0perdasTecnicasOpenDSS\Recursos\CurvasTxt\CurvasDeCargaDU.dss"

        ! Arquivo de condutores
        Redirect "I:\SA\GRMP\PERDAS-TECNICAS\0perdasTecnicasOpenDSS\Recursos\Condutores.dss"


      SET_TO text_line_data = ! manter este comentario para compatibilidade do C#
        new circuit.alim@Value(CodAlim) bus1=@Value(CodPonAcopl),basekv=@Value(_tensaoNom),pu=
    -> AttributeRemover_3
AttributeRemover_3
    REMOVE_ATTRS = NUMALM,REFSE,CodPonAcopl1,CodPonPEL,CodSegmMT,PEL
    -> FeatureMerger_3 [REQUESTOR]
SegmentoMT (input)
    -> FeatureMerger_2 [SUPPLIER]
    -> FeatureMerger_5 [SUPPLIER]
Note: obtem trecho p/ instalacao energymeter
FeatureMerger_2
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(CodPonAcopl) @Value(CodPonAcopl1) AUTO
    MERGED -> AttributeCreator_15
Note: energy meter
AttributeCreator_15
    ATTR_TABLE:
      SET_TO text_line_data =
        new energymeter.carga element=line.@Value(CodSegmMT),terminal=1
    -> FeatureMerger_14 [REQUESTOR]
FeatureMerger_5
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_3
AttributeCreator_3
    ATTR_TABLE = SET_TO linha2 = Redirect @Value(CodAlim)SegmentosMT.dss
    -> Aggregator
FeatureMerger_13_Supplier (input)
    -> FeatureMerger_13 [SUPPLIER]
FeatureMerger_13
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_12
    MERGED -> criaStringVoltageBases [temPT]
    NOT_MERGED -> criaStringVoltageBases [naoTemPT]
Note: criaStringVoltageBases
criaStringVoltageBases
    ALIM = @Value(Alim)
    -> FeatureMerger_14 [SUPPLIER]
Note: NergyMeter+CalcVoltagesBAse
FeatureMerger_14
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(Alim) AUTO
    MERGED -> StringConcatenator_3
StringConcatenator_3
    ACTION = Overwrite Existing Attributes
    PARM_LINE = @Value(text_line_data)@Value(linha3_2)
    ATTRLIST = text_line_data
    -> AttributeRemover
AttributeRemover
    REMOVE_ATTRS = CodSegmMT,NomeUsina,curvaOpenDSS,CodPonPEL,TENNOM,REFSE,CodPonAcopl1,linha3_2,Alim,_tensaoNom,PEL,CodBase,NUMALM
    -> ArquivoAnualB (output)
ArquivoAnualB (output)
AttributeCreator_12
    ATTR_TABLE = SET_TO linha2 = Redirect @Value(CodAlim)PT.dss
    -> Aggregator
SegmentoBT (input)
    -> FeatureMerger_6 [SUPPLIER]
FeatureMerger_6
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_2
AttributeCreator_2
    ATTR_TABLE = SET_TO linha2 = Redirect @Value(CodAlim)SegmentosBT.dss
    -> Aggregator
ReguladorMT (input)
    -> FeatureMerger_7 [SUPPLIER]
FeatureMerger_7
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_4
AttributeCreator_4
    ATTR_TABLE = SET_TO linha2 = Redirect @Value(CodAlim)Reguladores.dss
    -> Aggregator
Ramal (input)
    -> FeatureMerger_8 [SUPPLIER]
FeatureMerger_8
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_5
AttributeCreator_5
    ATTR_TABLE = SET_TO linha2 = Redirect @Value(CodAlim)Ramais.dss
    -> Aggregator
TrafoMTMTMTBT (input)
    -> FeatureMerger_9 [SUPPLIER]
FeatureMerger_9
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_6
AttributeCreator_6
    ATTR_TABLE = SET_TO linha2 = Redirect @Value(CodAlim)Transformadores.dss
    -> Aggregator
ChavesMT (input)
    -> FeatureMerger_12 [SUPPLIER]
FeatureMerger_12
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator_9
AttributeCreator_9
    ATTR_TABLE = SET_TO linha2 = Redirect @Value(CodAlim)ChavesMT.dss
    -> Aggregator
Aggregator
    MODE = Geometry - Assemble One Level
    CONCAT_ATTRS = linha2
    AGGREGATE_TYPE = Homogeneous Collection (If Possible)
    ACCUM_ATTRS_NAME = Get Attributes From One Representative Feature
    GROUP_BY = CodAlim
    ORDERED = No
    AGGREGATE -> AttributeRemover_2
AttributeRemover_2
    REMOVE_ATTRS = CodPonAcopl1,CodSegmMT,_count
    -> FeatureMerger_3 [SUPPLIER]
FeatureMerger_3
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> StringConcatenator
StringConcatenator
    ACTION = Create New Attribute
    PARM_LINE = @Value(linha1)@Value(linha2)
    VAL_ATTR = text_line_data
    -> ArquivoAnualA (output)
ArquivoAnualA (output)

FME custom transformer escreveAlimDSS

Parameters:
- ALIM = @Value(Alim)   # Alim
- CODPONACOPL1 = @Value(CodPonAcopl1)   # CodPonAcopl1
- CODSEGMMT = @Value(CodSegmMT)   # CodSegmMT
- CODALIM = @Value(CodAlim)   # CodAlim
- CODPONACOPL = @Value(CodPonAcopl)   # CodPonAcopl
- TEXT_LINE_DATA = @Value(text_line_data)   # Text Line Data
- _TENSAONOM = @Value(_tensaoNom)   # Tensaonom

segmentoBT (input)
    -> escreveAlimDSSMensal [SegmentoBT]
    -> escreveAlimDSSAnual [SegmentoBT]
Alim (input)
    -> escreveAlimDSSMensal [StringReplacer_4_Input]
    -> escreveAlimDSSAnual [StringReplacer_4_Input]
trafoMTMTMTBT (input)
    -> escreveAlimDSSMensal [TrafoMTMTMTBT]
    -> escreveAlimDSSAnual [TrafoMTMTMTBT]
cargaBT (input)
    -> escreveAlimDSSMensal [CargaBT]
cargaMT (input)
    -> escreveAlimDSSMensal [CargaMT]
chavesMT (input)
    -> escreveAlimDSSMensal [ChavesMT]
    -> escreveAlimDSSAnual [ChavesMT]
cabecaAlim (input)
    -> escreveAlimDSSMensal [CabecaAlim]
    -> escreveAlimDSSAnual [CabecaAlim]
segmentoMT (input)
    -> escreveAlimDSSMensal [SegmentoMT]
    -> escreveAlimDSSAnual [SegmentoMT]
PT (input)
    -> escreveAlimDSSMensal [FeatureMerger_13_Supplier]
    -> escreveAlimDSSAnual [FeatureMerger_13_Supplier]
RT (input)
    -> escreveAlimDSSMensal [ReguladorMT]
    -> escreveAlimDSSAnual [ReguladorMT]
ramal (input)
    -> escreveAlimDSSMensal [Ramal]
    -> escreveAlimDSSAnual [Ramal]
escreveAlimDSSMensal
    CODPONACOPL = @Value(CodPonAcopl)
    CODPONACOPL1 = @Value(CodPonAcopl1)
    CODSEGMMT = @Value(CodSegmMT)
    CODALIM = @Value(CodAlim)
    TEXT_LINE_DATA = @Value(text_line_data)
    _TENSAONOM = @Value(_tensaoNom)
    ALIM = @Value(Alim)
    Cabecalho -> cabeçalho1 (output)
    ArquivoB -> Output (output)
cabeçalho1 (output)
Output (output)
escreveAlimDSSAnual
    CODPONACOPL = @Value(CodPonAcopl)
    CODPONACOPL1 = @Value(CodPonAcopl1)
    CODSEGMMT = @Value(CodSegmMT)
    CODALIM = @Value(CodAlim)
    TEXT_LINE_DATA = @Value(text_line_data)
    _TENSAONOM = @Value(_tensaoNom)
    ALIM = @Value(Alim)
    ArquivoAnualB -> AnualB (output)
    ArquivoAnualA -> AnualA (output)
AnualA (output)
AnualB (output)

FME custom transformer AttributeCombiner
Combines specified attribute(s) of multiple features to form concatenated string(s). This transformer outputs a single feature for each group of input features, and the specified attribute(s) in the output feature will store the concatenated string(s). 
    This transformer always discards <null> and <missing> attributes. Regarding the empty string, you can control how to handle that with the "Drop Empty String" parameter. 
    The function is similar to the "Attributes to Concatenate" option of the Aggregator, but this transformer does not aggregate features. The geometry and unspecified attributes of any one feature for each group will be preserved, but others will be discarded. 
    This transformer can be used to concatenate specific attributes of many features efficiently, if you don't need to perform feature aggregation.
    Note: This transformer contains a Python script, which was tested with Python 2.7 interpreter. It may NOT work with Python 3.x interpreter.
Parameters
    Group By
    : 
    If you specify one or more attributes in this parameter, the concatenation will be performed for each group of features which have the same value(s) for the specified attribute(s).
    Input is Ordered by Group
    :
    If you are sure that the input features are sorted by the "Group By" attributes, you can set "Yes" to this parameter so that the processing will be performed with the best performance.
    Attributes to Combine
    :
    Select attributes that should be combined.
    Maximum Number of Features to Combine
    :
    Optionally you can specify the maximum number of features to combine into one. The number must be an integer greater than 0. Otherwise, the setting will be ignored. 
    Note that the number specified with this parameter indicates the maximum number of processed features at once. The number of concatenated attributes could be less than the maximum, since <null> and <missing> (and <empty> if you set "Yes" to the "Drop Empty String" parameter) attributes will be discarded. 
    Drop Empty String
    :
    By default, this transformer treats the empty string as a valid value which should be concatenated. If you don't want to concatenate empty strings, set "Yes" to this parameter.
    Delimiter String
    :
    Specify a character string that should be used as a delimiter string to separate individual values. You can also leave blank this parameter not to use any delimiter.
    Surround Each Value With
    :
    Optionally you can select a pair of symbols (e.g. single quotation marks) that will surround each value before concatenating. 
    Prefix for Each Value
    : 
    Optionally you can specify a prefix string that will be added to each value. 
    Suffix for Each Value
    : 
    Optionally you can specify a suffix string that will be added to each value.
Copyright (c) 2016 pragmatica inc. 
    Permission is granted to anyone, free of charge, to use, modify and distribute the object code form of this transformer for any purpose, subject to the following restrictions: 
    1) The origin of this transformer and associated FME(R) software must not be misrepresented. 
    2) This transformer may only be used in conjunction with a validly licensed copy of FME software. 
    THIS SOFTWARE IS PROVIDED BY PRAGMATICA INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL PRAGMATICA INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- GROUP_BY =   # " " Group By
- ORDERED_BY_GROUP = No   # Input is Ordered by Group
- ATTRS =   # " " Attributes to Combine
- MAX_NUM =   # Maximum Number of Features to Combine
- DROP_EMPTY = No   # Drop Empty String
- DELIM = ,   # Delimiter String
- QUOT = None
- PREFIX =   # Prefix for Each Value
- SUFFIX =   # Suffix for Each Value

Input (input)
    -> ParameterFetcher
ParameterFetcher
    ATTR_LIST = __tmp.group_by {$(GROUP_BY)} __tmp.attrs {$(ATTRS)} __tmp.max_num {$(MAX_NUM)} __tmp.delim {$(DELIM)} __tmp.drop_empty {$(DROP_EMPTY)} __tmp.quot {$(QUOT)} __tmp.prefix {$(PREFIX)} __tmp.suffix {$(SUFFIX)}
    -> TclCaller
TclCaller
    NEW_ATTRIBUTES = __tmp.attr{}
    SRC:
      proc preProcessToCombine {} {
          set i 0
          foreach attr [FME_GetAttribute "__tmp.attrs"] {
              FME_SetAttribute "__tmp.attr{$i}" $attr
              incr i
          }
          set num [FME_GetAttribute "__tmp.max_num"]
          if {![string is integer -strict $num]} {
              FME_SetAttribute "__tmp.max_num" 0
          }
          set group {}
          foreach attr [FME_GetAttribute "__tmp.group_by"] {
              if {![FME_AttributeExists $attr]} {
                  lappend group "\a"
              } elseif {[FME_IsAttributeNull $attr]} {
                  lappend group "\b"
              } else {
                  lappend group [FME_GetAttribute $attr]
              }
          }
          return [join $group {_}]
      }
    TCLPROG = preProcessToCombine
    VAL_ATTR = __tmp.group
    -> Tester
Tester
    TEST_DESCRIPTION = ""
    TEST_MODE = Automatic
    TEST_CLAUSE:
      TEST @Value(__tmp.group_by) = ""
      TEST $(ORDERED_BY_GROUP) = Yes
    BOOL_OP = OR
    PASSED -> PythonCaller
    FAILED -> Sorter
Sorter
    SORT_PARM = __tmp.group ALPHA ASCENDING
    SORTED -> PythonCaller
PythonCaller
    PYTHONSYMBOL = AttributeCombiner
    PYTHONSOURCE:
      # 2016-04-13,  Takashi Iijima,  Original Implementation

      import fme
      import fmeobjects, locale

      class AttributeCombiner(object):
          def __init__(self):
              loc = locale.getdefaultlocale()
              enc = loc[1] if loc else 'utf_8'
              self.toStr = lambda s: s.encode(enc) if isinstance(s, unicode) else str(s)
              self.reset(None, None)

          def reset(self, group, feature):
              self.group = group # group ID value
              self.feature = feature # first feature for each group
              self.data = {} # key: attribute name, value: list of attribute values
              self.count = 0 # counter for number of features to combine

          def input(self, feature):
              group = feature.getAttribute('__tmp.group')
              num = int(feature.getAttribute('__tmp.max_num'))
              if group != self.group or (0 < num and num <= self.count):
                  self.output()
                  self.reset(group, feature)
              for attr in feature.getAttribute('__tmp.attr{}'):
                  attr = self.toStr(attr)
                  isNull, isMissing, type = feature.getAttributeNullMissingAndType(attr)
                  if not isNull and not isMissing:
                      self.data.setdefault(attr, []).append('%s' % feature.getAttribute(attr))
              self.count += 1

          def close(self):
              self.output()

          def output(self):
              if self.feature:
                  fmt = self.getFormat()
                  delim = self.feature.getAttribute('__tmp.delim')
                  if self.feature.getAttribute('__tmp.drop_empty') == 'Yes':
                      for attr, values in self.data.iteritems():
                          self.feature.setAttribute(attr, delim.join([fmt % v for v in values if v != '']))
                  else:
                      for attr, values in self.data.iteritems():
                          self.feature.setAttribute(attr, delim.join([fmt % v for v in values]))
                  self.pyoutput(self.feature)

          def getFormat(self):
              formats = {
                  'Single': '\'%s%%s%s\'' ,
                  'Double': '"%s%%s%s"' ,
                  'Round': '(%s%%s%s)',
                  'Curly': '{%s%%s%s}',
                  'Square': '[%s%%s%s]',
                  'Inequality': '<%s%%s%s>',
                  'None': '%s%%s%s'
              }
              option = self.feature.getAttribute('__tmp.quot')
              prefix= self.feature.getAttribute('__tmp.prefix')
              suffix = self.feature.getAttribute('__tmp.suffix')
              return formats[option] % (prefix, suffix)
    -> AttributeRemover
AttributeRemover
    LIST_ATTRS = __tmp.attr{}
    REMOVE_ATTRS = __tmp.attrs,__tmp.delim,__tmp.drop_empty,__tmp.group,__tmp.group_by,__tmp.max_num,__tmp.prefix,__tmp.quot,__tmp.suffix
    -> Output (output)
Output (output)

FME custom transformer escreveSegmentoBT

Parameters:
- CODFAS = @Value(CodFas)   # CodFas
- CODPONACOPL1 = @Value(CodPonAcopl1)   # CodPonAcopl1
- CODPONACOPL2 = @Value(CodPonAcopl2)   # CodPonAcopl2
- CODSEGMBT = @Value(CodSegmBT)   # CodSegmBT
- COMP_KM = @Value(Comp_km)   # Comp Km
- CODCOND = @Value(CodCond)   # CodCond
- CODALIM = @Value(CodAlim)   # CodAlim

Input (input)
    -> AttributeValueMapper_3
Note: barrasDSS
AttributeValueMapper_3
    LUT = AN,.1.0,BN,.1.0,CN,.1.0,ABN,.1.2.0,BCN,.1.2.0,CAN,.1.2.0,ABCN,.1.2.3.0
    DIRECTION = Forward (Source To Destination)
    SRC = CodFas
    VAL_ATTR = _barrasDSS
    -> AttributeValueMapper_4
Note: fasesDSS
AttributeValueMapper_4
    LUT = A,1,B,1,C,1,AB,2,BC,2,CA,2,ABC,3,AN,1,BN,1,CN,1,ABN,2,BCN,2,CAN,2,ABCN,3
    DIRECTION = Forward (Source To Destination)
    SRC = CodFas
    VAL_ATTR = _fasesDSS
    -> StringReplacer
StringReplacer
    REGEXP = NO
    SRC_ATTRS = Comp_km
    REPLACE_TEXT = .
    FIND_TEXT = ,
    NO_MATCH = _FME_NO_OP_
    CASE = NO
    -> AttributeCreator_2
Note: linha
AttributeCreator_2
    ATTR_TABLE = SET_TO text_line_data = new line.@Value(CodSegmBT) bus1=@Value(CodPonAcopl1)@Value(_barrasDSS),bus2=@Value(CodPonAcopl2)@Value(_barrasDSS),Phases=@Value(_fasesDSS),Linecode=@Value(CodCond),Length=@Value(Comp_km),Units=km
    -> AttributeRemover
AttributeRemover
    REMOVE_ATTRS = CodCond,CodSegmBT,Comp_km,_fasesDSS,CodPonAcopl1,_barrasDSS,CodFas,CodPonAcopl2
    -> Output (output)
Output (output)

FME custom transformer escreveTrafoMTBT_DSS

Parameters:
- CODTRAFO = @Value(CodTrafo)   # CodTrafo
- POTNOM_KVA = @Value(PotNom_kVA)   # Potnom Kva
- PERDVZ__ = @Value(PerdVz_%)   # Perdvz %
- TIPTRAFO = @Value(TipTrafo)   # TipTrafo
- CODFASSECU = @Value(CodFasSecu)   # CodFasSecu
- PERDTTL__ = @Value(PerdTtl_%)   # Perdttl %
- CODPONACOPL1 = @Value(CodPonAcopl1)   # CodPonAcopl1
- CODBNC = @Value(CodBnc)   # CodBnc
- CODFASPRIM = @Value(CodFasPrim)   # CodFasPrim
- CODFASTERC = @Value(CodFasTerc)   # CodFasTerc
- CODPONACOPL2 = @Value(CodPonAcopl2)   # CodPonAcopl2
- REATHL__ = @Value(ReatHL_%)   # Reathl %
- REATHT__ = @Value(ReatHT_%)   # Reatht %
- REATLT__ = @Value(ReatLT_%)   # Reatlt %
- RESIS__ = @Value(Resis_%)   # Resis %
- TENSECU_KV = @Value(TenSecu_kV)   # Tensecu Kv
- CODALIM = @Value(CodAlim)   # CodAlim
- PROPR = @Value(Propr)   # Propr
- SEMCARGA = @Value(SemCarga)   # SemCarga
- DESCR = @Value(Descr)   # Descr
- boolFiltraTrafoVazio = 0
- TAP_PU = @Value(Tap_pu)   # Tap Pu

AttributeCreator_3_Input (input)
    -> AttributeRenamer
Note: tensao ALTA
AttributeRenamer
    ATTR_TABLE = RENAME_SET_DEFAULT Descr > _kVBase
    -> AttributeRounder
AttributeRounder
    ROUND_TYPE = Nearest
    SRC_ATTRS = _kVBase
    PLACES = 2
    -> Tester_3
Note: Se tensao ALTA não existe
Tester_3
    TEST_DESCRIPTION = ""
    TEST_MODE = Automatic
    TEST_CLAUSE:
      TEST _kVBase ATTRIBUTE_VALUE_NULL ""
      TEST _kVBase ATTRIBUTE_IS_EMPTY ""
      TEST _kVBase ATTRIBUTE_IS_MISSING ""
    BOOL_OP = OR
    PASSED -> AttributeCreator_5
    FAILED -> AttributeRemover
AttributeCreator_5
    ATTR_TABLE = SET_TO vAltaFN = 13.8
    -> AttributeRemover
AttributeRemover
    REMOVE_ATTRS = CodBnc
    -> Tester_2
Note: Filtra trafos de terceiros
Tester_2
    TEST_DESCRIPTION = ""
    TEST_MODE = Automatic
    TEST_CLAUSE = TEST @Value(Propr) = PR
    BOOL_OP = OR
    PASSED -> Tester_5
    PASSED -> StringReplacer
Note: substitui ',' p/ '.'
StringReplacer
    REGEXP = NO
    SRC_ATTRS = ReatLT_%,Resis_%,ReatHT_%,PerdTtl_%,ReatHL_%,Tap_pu,PerdVz_%
    REPLACE_TEXT = .
    FIND_TEXT = ,
    NO_MATCH = _FME_NO_OP_
    CASE = NO
    -> AttributeValueMapper_5
Note: barrasDSS prim
AttributeValueMapper_5
    LUT = A,.1,B,.1,C,.1,AB,.1.2,BC,.1.2,CA,.1.2,ABC,.1.2.3
    DIRECTION = Forward (Source To Destination)
    SRC = CodFasPrim
    VAL_ATTR = _barrasPrimDSS
    -> AttributeValueMapper_7
Note: fasesDSS
AttributeValueMapper_7
    LUT = 2,1,4,3
    DIRECTION = Forward (Source To Destination)
    SRC = TipTrafo
    VAL_ATTR = _fasesDSS
    -> StringFormatter
StringFormatter
    SRC_ATTRS = _kVBase
    FORMAT = .2f
    -> AttributeFilter
AttributeFilter
    ATTR_VALUES = <EMPTY>,<MISSING>,<NULL>,<UNFILTERED>,7.97,13.80,12.70,22.00,19.92,34.50
    ATTR_NAME = _kVBase
    <EMPTY> -> AttributeCreator_4
    <EMPTY> -> Inspector_3
    <MISSING> -> AttributeCreator_4
    <MISSING> -> Inspector_3
    <NULL> -> AttributeCreator_4
    <NULL> -> Inspector_3
    <UNFILTERED> -> AttributeCreator_4
    <UNFILTERED> -> Inspector_3
    7.97 -> AttributeCreator_4
    13.80 -> AttributeCreator_4
    12.70 -> AttributeCreator_10
    22.00 -> AttributeCreator_10
    19.92 -> AttributeCreator_11
    34.50 -> AttributeCreator_11
Inspector_3 [off]
Note: niveis de tensao alimentador
AttributeCreator_4
    ATTR_TABLE:
      SET_TO nivelTensaoATFF = 13.80
      SET_TO nivelTensaoATFN = 7.97
    -> AttributeCreator
AttributeCreator_10
    ATTR_TABLE:
      SET_TO nivelTensaoATFF = 22.0
      SET_TO nivelTensaoATFN = 12.70
    -> AttributeCreator
AttributeCreator_11
    ATTR_TABLE:
      SET_TO nivelTensaoATFF = 34.5
      SET_TO nivelTensaoATFN = 19.92
    -> AttributeCreator
Note: calcula _perdaCobre
AttributeCreator
    ATTR_TABLE = SET_TO _perdaCobre = @sum(@Value(PerdTtl_%),@mult(-1,@Value(PerdVz_%)))
    -> Tester
Note: verifica SE É MONOFÁSICO
Tester
    TEST_DESCRIPTION = ""
    TEST_MODE = Automatic
    TEST_CLAUSE = TEST @Value(_fasesDSS) = 1
    BOOL_OP = OR
    PASSED -> AttributeValueMapper_4
    FAILED -> AttributeValueMapper_2
Note: tensaoFF para FN
AttributeValueMapper_4
    LUT = 0.24,0.12
    DIRECTION = Forward (Source To Destination)
    SRC = TenSecu_kV
    VAL_ATTR = TenSecu_kV
    -> AttributeValueMapper_6
Note: barrasDSS secu
AttributeValueMapper_6
    LUT = AN,.1.0,BN,.1.0,CN,.1.0
    DIRECTION = Forward (Source To Destination)
    SRC = CodFasSecu
    VAL_ATTR = _barrasSecuDSS
    -> AttributeValueMapper_8
Note: barrasDSS terc
AttributeValueMapper_8
    LUT = AN,.0.2,BN,.0.2,CN,.0.2
    DIRECTION = Forward (Source To Destination)
    SRC = CodFasTerc
    VAL_ATTR = _barrasTercDSS
    -> AttributeCreator_8
    -> AttributeCreator_12
Note: linha com reatancia.
AttributeCreator_12
    ATTR_TABLE = SET_TO text_line_data = new transformer.@Value(CodTrafo) Phases=1,Windings=3,Buses=[@Value(CodPonAcopl1)@Value(_barrasPrimDSS) @Value(CodPonAcopl2)@Value(_barrasSecuDSS) @Value(CodPonAcopl2)@Value(_barrasTercDSS)],Conns=[wye wye wye],kvs=[@Value(nivelTensaoATFN) 0.12 0.12],kvas=[@Value(PotNom_kVA) @Value(PotNom_kVA) @Value(PotNom_kVA)],Taps=[1.0 @Value(Tap_pu) @Value(Tap_pu)],XscArray=[@Value(ReatHL_%),@Value(ReatHT_%),@Value(ReatLT_%)],%loadloss=@Value(_perdaCobre),%noloadloss=@Value(PerdVz_%)
    -> AttributeRemover_2
Note: modelagem KERSTING
AttributeCreator_8 [off]
    ATTR_TABLE:
      SET_TO r0 = @mult(@sub(@Value(PerdTtl_%),@Value(PerdVz_%)),0.5)
      SET_TO r1 = @sub(@Value(PerdTtl_%),@Value(PerdVz_%))
      SET_TO r2 = @Value(r1)
    -> AttributeCreator_6
Note: linha com reatancia
AttributeCreator_6 [off]
    ATTR_TABLE = SET_TO text_line_data = new transformer.@Value(CodTrafo) Phases=1,Windings=3,Buses=[@Value(CodPonAcopl1)@Value(_barrasPrimDSS) @Value(CodPonAcopl2)@Value(_barrasSecuDSS) @Value(CodPonAcopl2)@Value(_barrasTercDSS)],Conns=[LN wye wye],kvs=[@Value(nivelTensaoATFN) @Value(TenSecu_kV) @Value(TenSecu_kV)],kvas=[@Value(PotNom_kVA) @Value(PotNom_kVA) @Value(PotNom_kVA)],%Rs=[@Value(r0) @Value(r1) @Value(r2)],XHL=@Value(ReatHL_%),XHT=@Value(ReatHT_%),XLT=@Value(ReatLT_%),%noloadloss=@Value(PerdVz_%)
    -> AttributeRemover_2
Note: barrasDSS secu
AttributeValueMapper_2
    LUT = AB,.1.2.0,BC,.1.2.0,CA,.1.2.0,ABCN,.1.2.3.0
    DIRECTION = Forward (Source To Destination)
    SRC = CodFasSecu
    VAL_ATTR = _barrasSecuDSS
    -> AttributeCreator_13
Note: linha com reatancia.
AttributeCreator_13
    ATTR_TABLE = SET_TO text_line_data = new transformer.@Value(CodTrafo) Phases=3,Windings=2,Buses=[@Value(CodPonAcopl1)@Value(_barrasPrimDSS) @Value(CodPonAcopl2)@Value(_barrasSecuDSS)],Conns=[delta wye],kvs=[@Value(nivelTensaoATFF) 0.220],kvas=[@Value(PotNom_kVA) @Value(PotNom_kVA)],Taps=[1.0 @Value(Tap_pu)],XHL=@Value(ReatHL_%),%loadloss=@Value(_perdaCobre),%noloadloss=@Value(PerdVz_%)
    -> AttributeRemover_2
AttributeRemover_2
    REMOVE_ATTRS = CodTrafo,CodFasPrim,TenSecu_kV,PerdVz_%,CodPonAcopl1,ReatHT_%,PotNom_kVA,_barrasPrimDSS,CodPonAcopl2,nivelTensaoATFN,PerdTtl_%,_fasesDSS,nivelTensaoATFF,ReatLT_%,TipTrafo,ReatHL_%,Resis_%,r1,_barrasSecuDSS,_barrasTercDSS,r0,r2,_kVBase,CodFasTerc,vAltaFN,CodFasSecu,imag
    -> Inspector
    -> AttributeCreator_3_Output (output)
Inspector [off]
AttributeCreator_3_Output (output)
Note: Filtra trafos a vazio :(
Tester_4
    TEST_DESCRIPTION = ""
    TEST_MODE = Automatic
    TEST_CLAUSE = TEST $(boolFiltraTrafoVazio) = 1
    BOOL_OP = OR
    PASSED -> Tester_5
Note: Filtra trafos a vazio :(
Tester_5
    COMPOSITE_TEST = "1 AND 2"
    TEST_DESCRIPTION = ""
    TEST_MODE = Automatic
    TEST_CLAUSE:
      TEST @Value(SemCarga) != 1
      TEST $(boolFiltraTrafoVazio) = 0
    BOOL_OP = COMPOSITE
    FAILED -> Inspector_2
Inspector_2 [off]

FME custom transformer escrevePT

Parameters:
- CODALIM = @Value(CodAlim)   # CodAlim
- CODFASPRIM = @Value(CodFasPrim)   # CodFasPrim
- CODPONACOPL1 = @Value(CodPonAcopl1)   # CodPonAcopl1
- CODPONACOPL2 = @Value(CodPonAcopl2)   # CodPonAcopl2
- DESCR = @Value(Descr)   # Descr
- PERDTTL__ = @Value(PerdTtl_%)   # Perdttl %
- PERDVZ__ = @Value(PerdVz_%)   # Perdvz %
- POTNOM_KVA = @Value(PotNom_kVA)   # Potnom Kva
- REATHL__ = @Value(ReatHL_%)   # Reathl %
- RESIS__ = @Value(Resis_%)   # Resis %
- TENSECU_KV = @Value(TenSecu_kV)   # Tensecu Kv
- CODBNC = @Value(CodBnc)   # CodBnc
- TIPTRAFO = @Value(TipTrafo)   # TipTrafo
- CODTRAFO = @Value(CodTrafo)   # CodTrafo
- CODFASSECU = @Value(CodFasSecu)   # CodFasSecu

Input (input)
    -> StringReplacer
Note: substitui ',' p/ '.'
StringReplacer
    REGEXP = NO
    SRC_ATTRS = PerdTtl_%,Resis_%,PerdVz_%,ReatHL_%,TenSecu_kV
    REPLACE_TEXT = .
    FIND_TEXT = ,
    NO_MATCH = _FME_NO_OP_
    CASE = NO
    -> AttributeValueMapper_5
Note: barrasDSS prim
AttributeValueMapper_5
    LUT = AB,.1.2,BC,.2.3,CA,.3.1
    DIRECTION = Forward (Source To Destination)
    SRC = CodFasPrim
    VAL_ATTR = _barrasPrimDSS
    -> AttributeValueMapper_8
Note: barrasDSS secundaria
AttributeValueMapper_8
    LUT = AN,.1.0,BN,.2.0,CN,.3.0
    DIRECTION = Forward (Source To Destination)
    SRC = CodFasSecu
    VAL_ATTR = _barrasSecDSS
    -> AttributeValueMapper_7
Note: fasesDSS / OBS: 1=mono a 2 fios / 2= mono a 3fios
AttributeValueMapper_7
    LUT = 1,1,4,3
    DIRECTION = Forward (Source To Destination)
    SRC = TipTrafo
    VAL_ATTR = _fasesDSS
    -> Tester_3
Note: Verifica se eh abaixador/levantador
Tester_3
    TEST_DESCRIPTION = ""
    TEST_MODE = Automatic
    TEST_CLAUSE = TEST @Value(Descr) = abaixador
    BOOL_OP = OR
    PASSED -> AttributeCreator_9
    FAILED -> AttributeCreator_3
Note: PT abaixador / linha com reatancia.
AttributeCreator_9
    ATTR_TABLE = SET_TO text_line_data = new transformer.@Value(CodTrafo)-@Value(CodFasPrim) Phases=1,Windings=2,Buses=[@Value(CodPonAcopl1)@Value(_barrasPrimDSS) @Value(CodPonAcopl2)@Value(_barrasSecDSS)],Conns=[delta LN],kvs=[34.5 7.97],kvas=[@Value(PotNom_kVA) @Value(PotNom_kVA)],%loadloss=@sub(@Value(PerdTtl_%),@Value(PerdVz_%)),XHL=@Value(ReatHL_%),%noloadloss=@Value(PerdVz_%)
    -> AttributeRemover_2
Note: PT elevador / linha com reatancia.
AttributeCreator_3
    ATTR_TABLE = SET_TO text_line_data = new transformer.@Value(CodTrafo)-@Value(CodFasPrim) Phases=1,Windings=2,Buses=[@Value(CodPonAcopl1)@Value(_barrasPrimDSS) @Value(CodPonAcopl2)@Value(_barrasSecDSS)],Conns=[delta LN],kvs=[13.8 19.92],kvas=[@Value(PotNom_kVA) @Value(PotNom_kVA)],%loadloss=@sub(@Value(PerdTtl_%),@Value(PerdVz_%)),XHL=@Value(ReatHL_%),%noloadloss=@Value(PerdVz_%)
    -> AttributeRemover_2
AttributeRemover_2
    REMOVE_ATTRS = _barrasTercDSS,PerdTtl_%,_fasesDSS,CodFasPrim,Resis_%,Descr,CodPonAcopl2,TipTrafo,PotNom_kVA,CodTrafo,PerdVz_%,ReatHL_%,_barrasPrimDSS,CodPonAcopl1,CodBnc,TenSecu_kV
    -> Output (output)
    -> Inspector
Output (output)
Inspector [off]

FME custom transformer verificaGDMT_Anual

Parameters:
- MED_KWH__MAR = @Value(Med(kWh)_Mar)   # Med(kwh) Mar
- MED_KWH__FEV = @Value(Med(kWh)_Fev)   # Med(kwh) Fev
- MED_KWH__JUL = @Value(Med(kWh)_Jul)   # Med(kwh) Jul
- MED_KWH__JAN = @Value(Med(kWh)_Jan)   # Med(kwh) Jan
- MED_KWH__NOV = @Value(Med(kWh)_Nov)   # Med(kwh) Nov
- MED_KWH__ABR = @Value(Med(kWh)_Abr)   # Med(kwh) Abr
- EQPTO_PNTINJECAO = @Value(Eqpto/PntInjecao)   # Eqpto/PntInjecao
- MED_KWH__SET = @Value(Med(kWh)_Set)   # Med(kwh) Set
- TIPOEQPTO = @Value(TipoEqpto)   # TipoEqpto
- CODBASE = @Value(CodBase)   # CodBase
- MED_KWH__OUT = @Value(Med(kWh)_Out)   # Med(kwh) Out
- MED_KWH__AGO = @Value(Med(kWh)_Ago)   # Med(kwh) Ago
- MED_KWH__MAI = @Value(Med(kWh)_Mai)   # Med(kwh) Mai
- NOMEUSINA = @Value(NomeUsina)   # NomeUsina
- CURVAOPENDSS = @Value(curvaOpenDSS)   # curvaOpenDSS
- MED_KWH__DEZ = @Value(Med(kWh)_Dez)   # Med(kwh) Dez
- ALIM = @Value(Alim)   # Alim
- MED_KWH__JUN = @Value(Med(kWh)_Jun)   # Med(kwh) Jun
- _TENSAONOM = @Value(_tensaoNom)   # Tensaonom
- CODALIM = @Value(CodAlim)   # CodAlim

getNivelTensao (input)
    -> verificaGDMT [getNivelTensao]
    -> verificaGDMT_2 [getNivelTensao]
    -> verificaGDMT_3 [getNivelTensao]
    -> verificaGDMT_4 [getNivelTensao]
    -> verificaGDMT_5 [getNivelTensao]
    -> verificaGDMT_6 [getNivelTensao]
    -> verificaGDMT_7 [getNivelTensao]
    -> verificaGDMT_8 [getNivelTensao]
    -> verificaGDMT_9 [getNivelTensao]
    -> verificaGDMT_10 [getNivelTensao]
    -> verificaGDMT_11 [getNivelTensao]
    -> verificaGDMT_12 [getNivelTensao]
AttributeCreator_Input (input)
    -> AttributeCreator
    -> AttributeCreator_2
    -> AttributeCreator_3
    -> AttributeCreator_4
    -> AttributeCreator_5
    -> AttributeCreator_6
    -> AttributeCreator_7
    -> AttributeCreator_8
    -> AttributeCreator_9
    -> AttributeCreator_10
    -> AttributeCreator_11
    -> AttributeCreator_12
Note: mês a calcular
AttributeCreator
    ATTR_TABLE = SET_TO mesACalcular = 1
    -> verificaGDMT [FeatureMerger_Requestor1]
AttributeCreator_2
    ATTR_TABLE = SET_TO mesACalcular = 2
    -> verificaGDMT_2 [FeatureMerger_Requestor1]
AttributeCreator_3
    ATTR_TABLE = SET_TO mesACalcular = 3
    -> verificaGDMT_3 [FeatureMerger_Requestor1]
AttributeCreator_4
    ATTR_TABLE = SET_TO mesACalcular = 4
    -> verificaGDMT_4 [FeatureMerger_Requestor1]
AttributeCreator_5
    ATTR_TABLE = SET_TO mesACalcular = 5
    -> verificaGDMT_5 [FeatureMerger_Requestor1]
AttributeCreator_6
    ATTR_TABLE = SET_TO mesACalcular = 6
    -> verificaGDMT_6 [FeatureMerger_Requestor1]
AttributeCreator_7
    ATTR_TABLE = SET_TO mesACalcular = 7
    -> verificaGDMT_7 [FeatureMerger_Requestor1]
AttributeCreator_8
    ATTR_TABLE = SET_TO mesACalcular = 8
    -> verificaGDMT_8 [FeatureMerger_Requestor1]
AttributeCreator_9
    ATTR_TABLE = SET_TO mesACalcular = 9
    -> verificaGDMT_9 [FeatureMerger_Requestor1]
AttributeCreator_10
    ATTR_TABLE = SET_TO mesACalcular = 10
    -> verificaGDMT_10 [FeatureMerger_Requestor1]
AttributeCreator_11
    ATTR_TABLE = SET_TO mesACalcular = 11
    -> verificaGDMT_11 [FeatureMerger_Requestor1]
AttributeCreator_12
    ATTR_TABLE = SET_TO mesACalcular = 12
    -> verificaGDMT_12 [FeatureMerger_Requestor1]
verificaGDMT_FeatureMerger_Supplier_1 (input)
    -> verificaGDMT [FeatureMerger_Supplier]
    -> verificaGDMT_3 [FeatureMerger_Supplier]
    -> verificaGDMT_4 [FeatureMerger_Supplier]
    -> verificaGDMT_5 [FeatureMerger_Supplier]
    -> verificaGDMT_6 [FeatureMerger_Supplier]
    -> verificaGDMT_7 [FeatureMerger_Supplier]
    -> verificaGDMT_9 [FeatureMerger_Supplier]
    -> verificaGDMT_10 [FeatureMerger_Supplier]
    -> verificaGDMT_11 [FeatureMerger_Supplier]
    -> verificaGDMT_12 [FeatureMerger_Supplier]
    -> verificaGDMT_2 [FeatureMerger_Supplier]
    -> verificaGDMT_8 [FeatureMerger_Supplier]
verificaGDMT
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_1 (output)
verificaGDMT_Output_1 (output)
verificaGDMT_2
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_2 (output)
verificaGDMT_Output_2 (output)
verificaGDMT_3
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_3 (output)
verificaGDMT_Output_3 (output)
verificaGDMT_4
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_4 (output)
verificaGDMT_Output_4 (output)
verificaGDMT_5
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_5 (output)
verificaGDMT_Output_5 (output)
verificaGDMT_6
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_6 (output)
verificaGDMT_Output_6 (output)
verificaGDMT_7
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_7 (output)
verificaGDMT_Output_7 (output)
verificaGDMT_8
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_8 (output)
verificaGDMT_Output_8 (output)
verificaGDMT_9
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_9 (output)
verificaGDMT_Output_9 (output)
verificaGDMT_10
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_10 (output)
verificaGDMT_Output_10 (output)
verificaGDMT_11
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_11 (output)
verificaGDMT_Output_11 (output)
verificaGDMT_12
    _TENSAONOM = @Value(_tensaoNom)
    MED_KWH__JUL = @Value(Med(kWh)_Jul)
    NOMEUSINA = @Value(NomeUsina)
    TIPOEQPTO = @Value(TipoEqpto)
    MED_KWH__ABR = @Value(Med(kWh)_Abr)
    MED_KWH__DEZ = @Value(Med(kWh)_Dez)
    MESACALCULAR = @Value(mesACalcular)
    MED_KWH__AGO = @Value(Med(kWh)_Ago)
    MED_KWH__OUT = @Value(Med(kWh)_Out)
    CODALIM = @Value(CodAlim)
    ALIM = @Value(Alim)
    MED_KWH__JAN = @Value(Med(kWh)_Jan)
    MED_KWH__SET = @Value(Med(kWh)_Set)
    MED_KWH__FEV = @Value(Med(kWh)_Fev)
    MED_KWH__JUN = @Value(Med(kWh)_Jun)
    MED_KWH__NOV = @Value(Med(kWh)_Nov)
    EQPTO_PNTINJECAO = @Value(Eqpto/PntInjecao)
    MED_KWH__MAI = @Value(Med(kWh)_Mai)
    CURVAOPENDSS = @Value(curvaOpenDSS)
    MED_KWH__MAR = @Value(Med(kWh)_Mar)
    CODBASE = @Value(CodBase)
    -> verificaGDMT_Output_12 (output)
verificaGDMT_Output_12 (output)

FME custom transformer escreveCargaMT

Parameters:
- CODCRVCRG = @Value(CodCrvCrg)   # CodCrvCrg
- DO = @Value(DO)
- DU = @Value(DU)
- SA = @Value(SA)
- CODFAS = @Value(CodFas)   # CodFas
- CODPONACOPL = @Value(CodPonAcopl)   # CodPonAcopl
- TIPCRVACARGA = @Value(TipCrvaCarga)   # TipCrvaCarga
- ENERMEDID01_MWH = @Value(EnerMedid01_MWh)   # Enermedid01 Mwh
- CODFAS_2 = @Value(CodFas)   # CodFas
- TIPCRVACARGA_2 = @Value(TipCrvaCarga)   # TipCrvaCarga
- CODCONSMT = @Value(CodConsMT)   # CodConsMT
- ENERMEDID01_MWH_2 = @Value(EnerMedid01_MWh)   # Enermedid01 Mwh
- CODALIM = @Value(CodAlim)   # CodAlim
- DESCR = @Value(Descr)   # Descr
- ENERMEDID02_MWH = @Value(EnerMedid02_MWh)   # Enermedid02 Mwh
- ENERMEDID03_MWH = @Value(EnerMedid03_MWh)   # Enermedid03 Mwh
- ENERMEDID04_MWH = @Value(EnerMedid04_MWh)   # Enermedid04 Mwh
- ENERMEDID05_MWH = @Value(EnerMedid05_MWh)   # Enermedid05 Mwh
- ENERMEDID06_MWH = @Value(EnerMedid06_MWh)   # Enermedid06 Mwh
- ENERMEDID07_MWH = @Value(EnerMedid07_MWh)   # Enermedid07 Mwh
- ENERMEDID08_MWH = @Value(EnerMedid08_MWh)   # Enermedid08 Mwh
- ENERMEDID09_MWH = @Value(EnerMedid09_MWh)   # Enermedid09 Mwh
- ENERMEDID10_MWH = @Value(EnerMedid10_MWh)   # Enermedid10 Mwh
- ENERMEDID11_MWH = @Value(EnerMedid11_MWh)   # Enermedid11 Mwh
- ENERMEDID12_MWH = @Value(EnerMedid12_MWh)   # Enermedid12 Mwh
- MESACALCULAR = @Value(mesACalcular)   # mesACalcular

Input (input)
    -> AttributeRenamer
Note: tensao
AttributeRenamer
    ATTR_TABLE = RENAME_SET_DEFAULT Descr > _kVBase
    -> Tester_2
Note: Se tensao não existe
Tester_2
    TEST_DESCRIPTION = ""
    TEST_MODE = Automatic
    TEST_CLAUSE:
      TEST _kVBase ATTRIBUTE_VALUE_NULL ""
      TEST _kVBase ATTRIBUTE_IS_EMPTY ""
      TEST _kVBase ATTRIBUTE_IS_MISSING ""
    BOOL_OP = OR
    PASSED -> AttributeCreator_5
    FAILED -> AttributeValueMapper_5
AttributeCreator_5
    ATTR_TABLE = SET_TO _kVBase = 13.8
    -> AttributeValueMapper_5
Note: barrasDSS
AttributeValueMapper_5
    LUT = AN,.1.0,BN,.1.0,CN,.1.0,ABN,.1.2.0,BCN,.1.2.0,CAN,.1.2.0,ABCN,.1.2.3.0
    DIRECTION = Forward (Source To Destination)
    SRC = CodFas
    VAL_ATTR = _barrasDSS
    -> AttributeValueMapper_6
Note: fasesDSS
AttributeValueMapper_6
    LUT = A,1,B,1,C,1,AB,2,BC,2,CA,2,ABC,3,AN,1,BN,1,CN,1,ABN,2,BCN,2,CAN,2,ABCN,3
    DIRECTION = Forward (Source To Destination)
    SRC = CodFas
    VAL_ATTR = _fasesDSS
    -> FeatureMerger [REQUESTOR]
CurvasDeCarga (input)
    -> FeatureMerger [SUPPLIER]
FeatureMerger
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(TipCrvaCarga) @Value(CodCrvCrg) AUTO
    MERGED -> estConsumoDemanda [AttributeValueMapper_4_Input]
estConsumoDemanda
    ENERMEDID07_MWH = @Value(EnerMedid07_MWh)
    ENERMEDID10_MWH = @Value(EnerMedid10_MWh)
    DO = @Value(DO)
    SA = @Value(SA)
    ENERMEDID04_MWH = @Value(EnerMedid04_MWh)
    ENERMEDID09_MWH = @Value(EnerMedid09_MWh)
    ENERMEDID02_MWH = @Value(EnerMedid02_MWh)
    MESACALCULAR = @Value(mesACalcular)
    ENERMEDID06_MWH = @Value(EnerMedid06_MWh)
    ENERMEDID08_MWH = @Value(EnerMedid08_MWh)
    ENERMEDID05_MWH = @Value(EnerMedid05_MWh)
    ENERMEDID03_MWH = @Value(EnerMedid03_MWh)
    ENERMEDID11_MWH = @Value(EnerMedid11_MWh)
    ENERMEDID01_MWH = @Value(EnerMedid01_MWh)
    ENERMEDID12_MWH = @Value(EnerMedid12_MWh)
    DU = @Value(DU)
    AttributeCreator_2_Output -> AttributeCreator_4
    AttributeCreator_2_Output -> AttributeCreator_3
Note: NOVO mod. Carga linha
AttributeCreator_4
    ATTR_TABLE:
      SET_TO text_line_data = new load.@Value(CodConsMT)M1 bus1=@Value(CodPonAcopl)@Value(_barrasDSS),Phases=@Value(_fasesDSS),kv=@Value(_kVBase),kw=@Value(demandakWdiv2),pf=0.92,Vminpu=0.93,Vmaxpu=1.5,model=2,daily=arqCurvaNorm@Value(TipCrvaCarga),status=variable
        new load.@Value(CodConsMT)M2 bus1=@Value(CodPonAcopl)@Value(_barrasDSS),Phases=@Value(_fasesDSS),kv=@Value(_kVBase),kw=@Value(demandakWdiv2),pf=0.92,Vminpu=0.93,Vmaxpu=1.5,model=3,daily=arqCurvaNorm@Value(TipCrvaCarga),status=variable
    -> Output (output)
Note: linha
AttributeCreator_3 [off]
    ATTR_TABLE = SET_TO text_line_data = new load.@Value(CodConsMT) bus1=@Value(CodPonAcopl)@Value(_barrasDSS),Phases=@Value(_fasesDSS),kv=@Value(_kVBase),kw=@Value(demandaKW),pf=0.92,Vminpu=0.92,model=8,zipv=(0.5,0.0,0.5,1.0,0.0,0.0,0.0),daily=arqCurvaNorm@Value(TipCrvaCarga),status=variable
    -> Output (output)
Output (output)

FME custom transformer tipo

Parameters:
- TIP_UNID = @Value(TIP_UNID)   # Tip Unid
- TIPOEQ = @Value(tipoeq)   # tipoeq
- FASESEQ = @Value(FASESEQ)
- COD_ID = @Value(COD_ID)   # Cod Id
- CODCHV = @Value(CodChv)   # CodChv

TIPO_UNID_Input (input)
    -> TIPO_UNID
TIPO_UNID: AttributeFilter
    ATTR_VALUES = <EMPTY>,<MISSING>,<NULL>,<UNFILTERED>,02,04,24,40,03,36,39,11,13,20,21,22,23,50,SC,27,28,37,38,60,61
    ATTR_NAME = tipoeq
    24 -> CHAVE_FUSIVEL
    40 -> CHAVE_FUSIVEL
    36 -> CHAVE_FUSIVEL
    39 -> CHAVE_FACA
    11 -> CHAVE_FACA_2
    20 -> CHAVE_GAS
    21 -> DISJUNTOR
    22 -> RELIGADOR
    23 -> SECCIONALIZADOR
    50 -> SECCIONALIZADOR
    SC -> SECCIONALIZADOR
    27 -> CHAVE_TRIPOLAR
    28 -> CHAVE_FACA_UNIPOLAR
CHAVE_FUSIVEL: StringConcatenator
    ACTION = Overwrite Existing Attributes
    PARM_LINE = 26
    ATTRLIST = TIP_UNID
    -> FASES
CHAVE_FACA: StringConcatenator
    ACTION = Overwrite Existing Attributes
    PARM_LINE = 23
    ATTRLIST = TIP_UNID
    -> FASES
CHAVE_FACA_2: StringConcatenator
    ACTION = Overwrite Existing Attributes
    PARM_LINE = 23
    ATTRLIST = TIP_UNID
    -> CHAVE_FACA_Output (output)
CHAVE_FACA_Output (output)
CHAVE_GAS: StringConcatenator
    ACTION = Overwrite Existing Attributes
    PARM_LINE = 18
    ATTRLIST = TIP_UNID
    -> FASES
DISJUNTOR: StringConcatenator
    ACTION = Overwrite Existing Attributes
    PARM_LINE = 38
    ATTRLIST = TIP_UNID
    -> DISJUNTOR_Output (output)
DISJUNTOR_Output (output)
RELIGADOR: StringConcatenator
    ACTION = Overwrite Existing Attributes
    PARM_LINE = 44
    ATTRLIST = TIP_UNID
    -> RELIGADOR_Output (output)
RELIGADOR_Output (output)
SECCIONALIZADOR: StringConcatenator
    ACTION = Overwrite Existing Attributes
    PARM_LINE = 48
    ATTRLIST = TIP_UNID
    -> SECCIONALIZADOR_Output (output)
SECCIONALIZADOR_Output (output)
CHAVE_TRIPOLAR: StringConcatenator
    ACTION = Overwrite Existing Attributes
    PARM_LINE = 37
    ATTRLIST = TIP_UNID
    -> CHAVE_TRIPOLAR_Output (output)
CHAVE_TRIPOLAR_Output (output)
CHAVE_FACA_UNIPOLAR: StringConcatenator
    ACTION = Overwrite Existing Attributes
    PARM_LINE = 25
    ATTRLIST = TIP_UNID
    -> FASES
FASES: AttributeFilter
    ATTR_VALUES = <EMPTY>,<MISSING>,<NULL>,<UNFILTERED>,1,2,3,4,5,6,7
    ATTR_NAME = FASESEQ
    1 -> CHAVE_GAS_Output (output)
    2 -> CHAVE_GAS_Output (output)
    3 -> CHAVE_GAS_Output (output)
    4 -> CODID
    4 -> CODID_2
    5 -> CODID
    5 -> CODID_2
    6 -> CODID
    6 -> CODID_2
    7 -> CODID
    7 -> CODID_2
    7 -> CODID_3
CODID: StringConcatenator
    ACTION = Overwrite Existing Attributes
    PARM_LINE = @Value(CodChv)A
    ATTRLIST = CodChv
    -> CHAVE_GAS_Output (output)
CODID_2: StringConcatenator
    ACTION = Overwrite Existing Attributes
    PARM_LINE = @Value(CodChv)B
    ATTRLIST = CodChv
    -> CHAVE_GAS_Output (output)
CODID_3: StringConcatenator
    ACTION = Overwrite Existing Attributes
    PARM_LINE = @Value(CodChv)C
    ATTRLIST = CodChv
    -> CHAVE_GAS_Output (output)
CHAVE_GAS_Output (output)

FME custom transformer escreveCargaMTAnual

Parameters:
- Mes = 1
- CODALIM = @Value(CodAlim)   # CodAlim
- CODCONSMT = @Value(CodConsMT)   # CodConsMT
- CODCRVCRG = @Value(CodCrvCrg)   # CodCrvCrg
- CODFAS = @Value(CodFas)   # CodFas
- CODPONACOPL = @Value(CodPonAcopl)   # CodPonAcopl
- DESCR = @Value(Descr)   # Descr
- DO = @Value(DO)
- DU = @Value(DU)
- E = @Value(E)
- ENERMEDID01_MWH = @Value(EnerMedid01_MWh)   # Enermedid01 Mwh
- ENERMEDID02_MWH = @Value(EnerMedid02_MWh)   # Enermedid02 Mwh
- ENERMEDID03_MWH = @Value(EnerMedid03_MWh)   # Enermedid03 Mwh
- ENERMEDID04_MWH = @Value(EnerMedid04_MWh)   # Enermedid04 Mwh
- ENERMEDID05_MWH = @Value(EnerMedid05_MWh)   # Enermedid05 Mwh
- ENERMEDID06_MWH = @Value(EnerMedid06_MWh)   # Enermedid06 Mwh
- ENERMEDID07_MWH = @Value(EnerMedid07_MWh)   # Enermedid07 Mwh
- ENERMEDID08_MWH = @Value(EnerMedid08_MWh)   # Enermedid08 Mwh
- ENERMEDID09_MWH = @Value(EnerMedid09_MWh)   # Enermedid09 Mwh
- ENERMEDID10_MWH = @Value(EnerMedid10_MWh)   # Enermedid10 Mwh
- ENERMEDID11_MWH = @Value(EnerMedid11_MWh)   # Enermedid11 Mwh
- ENERMEDID12_MWH = @Value(EnerMedid12_MWh)   # Enermedid12 Mwh
- SA = @Value(SA)
- TIPCRVACARGA = @Value(TipCrvaCarga)   # TipCrvaCarga

CurvasCarga (input)
    -> escreveCargaMT [CurvasDeCarga]
    -> escreveCargaMT_2 [CurvasDeCarga]
    -> escreveCargaMT_3 [CurvasDeCarga]
    -> escreveCargaMT_4 [CurvasDeCarga]
    -> escreveCargaMT_5 [CurvasDeCarga]
    -> escreveCargaMT_6 [CurvasDeCarga]
    -> escreveCargaMT_12 [CurvasDeCarga]
    -> escreveCargaMT_11 [CurvasDeCarga]
    -> escreveCargaMT_10 [CurvasDeCarga]
    -> escreveCargaMT_9 [CurvasDeCarga]
    -> escreveCargaMT_8 [CurvasDeCarga]
    -> escreveCargaMT_7 [CurvasDeCarga]
Input (input)
    -> AttributeCreator_1
    -> AttributeCreator_2
    -> AttributeCreator_3
    -> AttributeCreator_4
    -> AttributeCreator_5
    -> AttributeCreator_6
    -> AttributeCreator_7
    -> AttributeCreator_8
    -> AttributeCreator_9
    -> AttributeCreator_10
    -> AttributeCreator_11
    -> AttributeCreator_12
Note: mês a calcular
AttributeCreator_1
    ATTR_TABLE = SET_TO mesACalcular = 1
    -> escreveCargaMT
escreveCargaMT
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1 (output)
1 (output)
AttributeCreator_2
    ATTR_TABLE = SET_TO mesACalcular = 2
    -> escreveCargaMT_2
escreveCargaMT_2
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_2 (output)
1_2 (output)
AttributeCreator_3
    ATTR_TABLE = SET_TO mesACalcular = 3
    -> escreveCargaMT_3
escreveCargaMT_3
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_3 (output)
1_3 (output)
AttributeCreator_4
    ATTR_TABLE = SET_TO mesACalcular = 4
    -> escreveCargaMT_4
escreveCargaMT_4
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_4 (output)
1_4 (output)
AttributeCreator_5
    ATTR_TABLE = SET_TO mesACalcular = 5
    -> escreveCargaMT_5
escreveCargaMT_5
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_5 (output)
1_5 (output)
AttributeCreator_6
    ATTR_TABLE = SET_TO mesACalcular = 6
    -> escreveCargaMT_6
escreveCargaMT_6
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_6 (output)
1_6 (output)
AttributeCreator_7
    ATTR_TABLE = SET_TO mesACalcular = 7
    -> escreveCargaMT_7
escreveCargaMT_7
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_7 (output)
1_7 (output)
Note: mês a calcular
AttributeCreator_8
    ATTR_TABLE = SET_TO mesACalcular = 8
    -> escreveCargaMT_8
escreveCargaMT_8
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_8 (output)
1_8 (output)
AttributeCreator_9
    ATTR_TABLE = SET_TO mesACalcular = 9
    -> escreveCargaMT_9
escreveCargaMT_9
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_9 (output)
1_9 (output)
AttributeCreator_10
    ATTR_TABLE = SET_TO mesACalcular = 10
    -> escreveCargaMT_10
escreveCargaMT_10
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_10 (output)
1_10 (output)
AttributeCreator_11
    ATTR_TABLE = SET_TO mesACalcular = 11
    -> escreveCargaMT_11
escreveCargaMT_11
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_11 (output)
1_11 (output)
AttributeCreator_12
    ATTR_TABLE = SET_TO mesACalcular = 12
    -> escreveCargaMT_12
escreveCargaMT_12
    ENERMEDID07_MWH = @Value(EnerMedid07_MWh)
    ENERMEDID10_MWH = @Value(EnerMedid10_MWh)
    DO = @Value(DO)
    ENERMEDID01_MWH_2 = @Value(EnerMedid01_MWh)
    SA = @Value(SA)
    ENERMEDID04_MWH = @Value(EnerMedid04_MWh)
    ENERMEDID09_MWH = @Value(EnerMedid09_MWh)
    CODCONSMT = @Value(CodConsMT)
    ENERMEDID02_MWH = @Value(EnerMedid02_MWh)
    MESACALCULAR = @Value(mesACalcular)
    CODALIM = @Value(CodAlim)
    TIPCRVACARGA = @Value(TipCrvaCarga)
    ENERMEDID06_MWH = @Value(EnerMedid06_MWh)
    ENERMEDID08_MWH = @Value(EnerMedid08_MWh)
    CODFAS = @Value(CodFas)
    ENERMEDID05_MWH = @Value(EnerMedid05_MWh)
    DESCR = @Value(Descr)
    CODPONACOPL = @Value(CodPonAcopl)
    CODCRVCRG = @Value(CodCrvCrg)
    ENERMEDID03_MWH = @Value(EnerMedid03_MWh)
    ENERMEDID11_MWH = @Value(EnerMedid11_MWh)
    CODFAS_2 = @Value(CodFas)
    ENERMEDID01_MWH = @Value(EnerMedid01_MWh)
    DU = @Value(DU)
    ENERMEDID12_MWH = @Value(EnerMedid12_MWh)
    TIPCRVACARGA_2 = @Value(TipCrvaCarga)
    -> 1_12 (output)
1_12 (output)

FME custom transformer verificaGDMT

Parameters:
- CODBASE = @Value(CodBase)   # CodBase
- NOMEUSINA = @Value(NomeUsina)   # NomeUsina
- CURVAOPENDSS = @Value(curvaOpenDSS)   # curvaOpenDSS
- EQPTO_PNTINJECAO = @Value(Eqpto/PntInjecao)   # Eqpto/PntInjecao
- MED_KWH__ABR = @Value(Med(kWh)_Abr)   # Med(kwh) Abr
- MED_KWH__AGO = @Value(Med(kWh)_Ago)   # Med(kwh) Ago
- MED_KWH__DEZ = @Value(Med(kWh)_Dez)   # Med(kwh) Dez
- MED_KWH__FEV = @Value(Med(kWh)_Fev)   # Med(kwh) Fev
- MED_KWH__JAN = @Value(Med(kWh)_Jan)   # Med(kwh) Jan
- MED_KWH__JUL = @Value(Med(kWh)_Jul)   # Med(kwh) Jul
- MED_KWH__JUN = @Value(Med(kWh)_Jun)   # Med(kwh) Jun
- MED_KWH__MAI = @Value(Med(kWh)_Mai)   # Med(kwh) Mai
- MED_KWH__MAR = @Value(Med(kWh)_Mar)   # Med(kwh) Mar
- MED_KWH__NOV = @Value(Med(kWh)_Nov)   # Med(kwh) Nov
- MED_KWH__OUT = @Value(Med(kWh)_Out)   # Med(kwh) Out
- MED_KWH__SET = @Value(Med(kWh)_Set)   # Med(kwh) Set
- TIPOEQPTO = @Value(TipoEqpto)   # TipoEqpto
- MESACALCULAR = @Value(mesACalcular)   # mesACalcular
- _TENSAONOM = @Value(_tensaoNom)   # Tensaonom
- CODALIM = @Value(CodAlim)   # CodAlim
- ALIM = @Value(Alim)   # Alim

FeatureMerger_Requestor1 (input)
    -> FeatureMerger [REQUESTOR]
FeatureMerger_Supplier (input)
    -> StringReplacer_2
Note: retira ' mantendo a compatibilidade do / getNivelTensao
StringReplacer_2
    REGEXP = YES
    SRC_ATTRS = Alim
    FIND_TEXT = '
    CASE = NO
    -> FeatureMerger [SUPPLIER]
FeatureMerger
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(CodAlim) @Value(Alim) AUTO
    MERGED -> Tester_2
Note: verifica se é usina com injecao na barra SE
Tester_2
    TEST_DESCRIPTION = ""
    TEST_MODE = Automatic
    TEST_CLAUSE = TEST @Value(TipoEqpto) = NaBarraSE
    BOOL_OP = OR
    PASSED -> AttributeCreator_3
    FAILED -> AttributeCreator_4
Note: Atribui barra ficticia para acessante com injeção direto na SE
AttributeCreator_3
    ATTR_TABLE = SET_TO CodPonAcopl1 = @Value(Eqpto/PntInjecao)
    -> AttributeValueMapper
Note: adiciona ' ao nome do alim
AttributeCreator_4
    ATTR_TABLE = SET_TO CodAlim = '@Value(CodAlim)'
    -> Tester
Note: define se obterá o PEL na / tabela de Trafos ou Chaves
Tester
    TEST_DESCRIPTION = ""
    TEST_MODE = Automatic
    TEST_CLAUSE = TEST @Value(TipoEqpto) = Trafo
    BOOL_OP = OR
    PASSED -> SQLExecutor [INITIATOR]
    FAILED -> SQLExecutor_2 [INITIATOR]
SQLExecutor
    MSSQL_ADO_QUERY_FEATURE_TYPES_FOR_MERGE_FILTERS = Yes
    MSSQL_ADO_COMMAND_TIMEOUT = 30
    DATASET = GEOPERDAS_DAIMON2018
    COMBINE_ATTRS = Keep Result Attributes if Conflict
    EXPOSED_ATTRIBUTE_LIST = CodPonAcopl1
    SQL_STATEMENT:
      select CodPonAcopl1 from StoredTrafoMTMTMTBT where
      codtrafo like @Value(Eqpto/PntInjecao)
      and codAlim = @Value(Alim)
      and codBase = @Value(CodBase)
    COMBINE_GEOM = Initiator Geometry Only
    FORMAT = MSSQL_ADO
    MSSQL_ADO_NAMED_CONNECTION = GEOPERDAS_DAIMON2018
    RESULT -> AttributeValueMapper
SQLExecutor_2
    MSSQL_ADO_QUERY_FEATURE_TYPES_FOR_MERGE_FILTERS = Yes
    MSSQL_ADO_COMMAND_TIMEOUT = 30
    DATASET = GEOPERDAS_DAIMON2018
    COMBINE_ATTRS = Keep Result Attributes if Conflict
    EXPOSED_ATTRIBUTE_LIST = CodPonAcopl1
    SQL_STATEMENT:
      select CodPonAcopl1 from StoredChaveMT where
      Descr like @Value(Eqpto/PntInjecao)
      and CodAlim = @Value(Alim)
      and codBase = @Value(CodBase)
    COMBINE_GEOM = Initiator Geometry Only
    FORMAT = MSSQL_ADO
    MSSQL_ADO_NAMED_CONNECTION = GEOPERDAS_DAIMON2018
    RESULT -> AttributeValueMapper
Note: verifica qual o mês será montado o arquivo
AttributeValueMapper
    LUT = 1,@Value(Med(kWh)_Jan),2,@Value(Med(kWh)_Fev),3,@Value(Med(kWh)_Mar),4,@Value(Med(kWh)_Abr),5,@Value(Med(kWh)_Mai),6,@Value(Med(kWh)_Jun),7,@Value(Med(kWh)_Jul),8,@Value(Med(kWh)_Ago),9,@Value(Med(kWh)_Set),10,@Value(Med(kWh)_Out),11,@Value(Med(kWh)_Nov),12,@Value(Med(kWh)_Dez)
    DIRECTION = Forward (Source To Destination)
    SRC = mesACalcular
    VAL_ATTR = InjecaoMedia
    -> StringReplacer
Note: retira ' mantendo a compatibilidade do / getNivelTensao
StringReplacer
    REGEXP = YES
    SRC_ATTRS = CodAlim
    FIND_TEXT = '
    CASE = NO
    -> FeatureMerger_2 [REQUESTOR]
    -> Inspector_2
Inspector_2 [off]
getNivelTensao (input)
    -> FeatureMerger_2 [SUPPLIER]
    -> Inspector
FeatureMerger_2
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(Alim) @Value(CodAlim) AUTO
    MERGED -> AttributeCreator
AttributeCreator
    ATTR_TABLE:
      SET_TO linhaGD1 =
        new loadshape.curva npts=24,interval=1.0,mult=@Value(curvaOpenDSS)
      SET_TO linhaGD21 =
        new generator."@Value(NomeUsina)" phases=3,bus1=@Value(CodPonAcopl1),Kv=@Value(_tensaoNom),Kw=@Value(InjecaoMedia),Model=3,Pf=1,daily=curva,Status=Fixed
    -> StringConcatenator_2
Note: text_line_data
StringConcatenator_2
    ACTION = Create New Attribute
    PARM_LINE = @Value(linhaGD1)@Value(linhaGD21)
    VAL_ATTR = text_line_data
    -> AttributeCombiner_2
Note: combina as linhas de uma mesma tabela, / caso tenha mais de 1usina por alimentador
AttributeCombiner_2
    DROP_EMPTY = No
    ATTRS = text_line_data
    QUOT = None
    GROUP_BY = Alim
    -> Output (output)
Output (output)
Inspector [off]

FME custom transformer escreveCargaBT

Parameters:
- CODCRVCRG = @Value(CodCrvCrg)   # CodCrvCrg
- DO = @Value(DO)
- DU = @Value(DU)
- SA = @Value(SA)
- CODFAS = @Value(CodFas)   # CodFas
- CODCONSBT = @Value(CodConsBT)   # CodConsBT
- CODPONACOPL = @Value(CodPonAcopl)   # CodPonAcopl
- TIPCRVACARGA = @Value(TipCrvaCarga)   # TipCrvaCarga
- ENERMEDID01_MWH = @Value(EnerMedid01_MWh)   # Enermedid01 Mwh
- CODALIM = @Value(CodAlim)   # CodAlim
- ENERMEDID02_MWH = @Value(EnerMedid02_MWh)   # Enermedid02 Mwh
- ENERMEDID03_MWH = @Value(EnerMedid03_MWh)   # Enermedid03 Mwh
- ENERMEDID04_MWH = @Value(EnerMedid04_MWh)   # Enermedid04 Mwh
- ENERMEDID05_MWH = @Value(EnerMedid05_MWh)   # Enermedid05 Mwh
- ENERMEDID06_MWH = @Value(EnerMedid06_MWh)   # Enermedid06 Mwh
- ENERMEDID07_MWH = @Value(EnerMedid07_MWh)   # Enermedid07 Mwh
- ENERMEDID08_MWH = @Value(EnerMedid08_MWh)   # Enermedid08 Mwh
- ENERMEDID09_MWH = @Value(EnerMedid09_MWh)   # Enermedid09 Mwh
- ENERMEDID10_MWH = @Value(EnerMedid10_MWh)   # Enermedid10 Mwh
- ENERMEDID11_MWH = @Value(EnerMedid11_MWh)   # Enermedid11 Mwh
- ENERMEDID12_MWH = @Value(EnerMedid12_MWh)   # Enermedid12 Mwh
- MESACALCULAR = @Value(mesACalcular)   # mesACalcular
- CODTRAFO = @Value(CodTrafo)   # CodTrafo
- TIPTRAFO = @Value(TipTrafo)   # TipTrafo

Input (input)
    -> Tester_2
Note: verifica se consumo diferente 0
Tester_2
    TEST_DESCRIPTION = ""
    TEST_MODE = Automatic
    TEST_CLAUSE = TEST @Value(EnerMedid01_MWh) != 0
    BOOL_OP = OR
    PASSED -> AttributeValueMapper_5
Note: barrasDSS
AttributeValueMapper_5
    LUT = AN,.1.0,BN,.1.0,CN,.1.0,ABN,.1.2.0,BCN,.1.2.0,CAN,.1.2.0,ABCN,.1.2.3.0
    DIRECTION = Forward (Source To Destination)
    SRC = CodFas
    VAL_ATTR = _barrasDSS
    -> AttributeValueMapper_6
Note: fasesDSS
AttributeValueMapper_6
    LUT = A,1,B,1,C,1,AB,2,BC,2,CA,2,ABC,3,AN,1,BN,1,CN,1,ABN,2,BCN,2,CAN,2,ABCN,3
    DIRECTION = Forward (Source To Destination)
    SRC = CodFas
    VAL_ATTR = _fasesDSS
    -> Tester_3
Note: verifica TipTrafo
Tester_3
    TEST_DESCRIPTION = ""
    TEST_MODE = Automatic
    TEST_CLAUSE = TEST @Value(TipTrafo) = 2
    BOOL_OP = OR
    PASSED -> AttributeValueMapper_2
    FAILED -> AttributeValueMapper_3
Note: base kV
AttributeValueMapper_2
    LUT = A,0.12,B,0.12,C,0.12,AN,0.12,BN,0.12,CN,0.12,ABN,0.24,BCN,0.24,CAN,0.24
    DIRECTION = Forward (Source To Destination)
    SRC = CodFas
    VAL_ATTR = _basekV
    -> FeatureMerger [REQUESTOR]
Note: base kV
AttributeValueMapper_3
    LUT = AB,0.22,BC,0.22,CA,0.22,ABC,0.22,AN,0.127,BN,0.127,CN,0.127,ABN,0.22,BCN,0.22,CAN,0.22,ABCN,0.22
    DIRECTION = Forward (Source To Destination)
    SRC = CodFas
    VAL_ATTR = _basekV
    -> FeatureMerger [REQUESTOR]
CurvasDeCarga (input)
    -> FeatureMerger [SUPPLIER]
FeatureMerger
    IGNORE_NULLS = No
    REJECT_NULL_MISSING_KEYS = No
    MERGE_TYPE = Attributes Only
    PROCESS_DUPS = No
    ATTR_ACCUM_MODE = Merge Supplier
    SUPPLIERS_FIRST = No
    ATTR_CONFLICT_RES = Use Requestor
    JOIN_KEYS = @Value(TipCrvaCarga) @Value(CodCrvCrg) AUTO
    MERGED -> estConsumoDemanda [AttributeValueMapper_4_Input]
estConsumoDemanda
    ENERMEDID07_MWH = @Value(EnerMedid07_MWh)
    ENERMEDID10_MWH = @Value(EnerMedid10_MWh)
    DO = @Value(DO)
    SA = @Value(SA)
    ENERMEDID04_MWH = @Value(EnerMedid04_MWh)
    ENERMEDID09_MWH = @Value(EnerMedid09_MWh)
    ENERMEDID02_MWH = @Value(EnerMedid02_MWh)
    MESACALCULAR = @Value(mesACalcular)
    ENERMEDID06_MWH = @Value(EnerMedid06_MWh)
    ENERMEDID08_MWH = @Value(EnerMedid08_MWh)
    ENERMEDID05_MWH = @Value(EnerMedid05_MWh)
    ENERMEDID03_MWH = @Value(EnerMedid03_MWh)
    ENERMEDID11_MWH = @Value(EnerMedid11_MWh)
    ENERMEDID01_MWH = @Value(EnerMedid01_MWh)
    ENERMEDID12_MWH = @Value(EnerMedid12_MWh)
    DU = @Value(DU)
    AttributeCreator_2_Output -> Tester
Note: verifica IP
Tester
    TEST_DESCRIPTION = ""
    TEST_MODE = Automatic
    TEST_CLAUSE = TEST @Value(CodCrvCrg) = IP
    BOOL_OP = OR
    PASSED -> AttributeCreator_4
    PASSED -> AttributeCreator_6
    FAILED -> AttributeCreator_3
    FAILED -> AttributeCreator_7
Note: NOVO linha IP
AttributeCreator_4
    ATTR_TABLE:
      SET_TO text_line_data = new load.@Value(CodConsBT)M1 bus1=@Value(CodPonAcopl)@Value(_barrasDSS),Phases=@Value(_fasesDSS),kv=@Value(_basekV),kw=@Value(demandakWdiv2),pf=0.92,Vminpu=0.92,Vmaxpu=1.5,model=2,daily=curvaTipica@Value(TipCrvaCarga),status=variable
        new load.@Value(CodConsBT)M2 bus1=@Value(CodPonAcopl)@Value(_barrasDSS),Phases=@Value(_fasesDSS),kv=@Value(_basekV),kw=@Value(demandakWdiv2),pf=0.92,Vminpu=0.92,Vmaxpu=1.5,model=3,daily=curvaTipica@Value(TipCrvaCarga),status=variable
    -> AttributeRemover
Note: OLD CODE linha IP
AttributeCreator_6 [off]
    ATTR_TABLE = SET_TO text_line_data = new load.@Value(CodConsBT) bus1=@Value(CodPonAcopl)@Value(_barrasDSS),Phases=@Value(_fasesDSS),kv=@Value(_basekV),kw=@Value(demandaKW),pf=0.92,Vminpu=0.92,model=8,zipv=(0.5,0.0,0.5,1.0,0.0,0.0,0.0),daily=curvaTipica@Value(TipCrvaCarga),status=variable
    -> AttributeRemover
Note: OLD CODE linha carga BT
AttributeCreator_3 [off]
    ATTR_TABLE = SET_TO text_line_data = new load.@Value(CodConsBT) bus1=@Value(CodPonAcopl)@Value(_barrasDSS),Phases=@Value(_fasesDSS),kv=@Value(_basekV),kw=@Value(demandaKW),pf=0.92,Vminpu=0.92,model=8,zipv=(0.5,0.0,0.5,1.0,0.0,0.0,0.0),daily=arqCurvaNorm@Value(TipCrvaCarga),status=variable
    -> AttributeRemover
Note: NOVO - linha carga BT
AttributeCreator_7
    ATTR_TABLE:
      SET_TO text_line_data = new load.@Value(CodConsBT)M1 bus1=@Value(CodPonAcopl)@Value(_barrasDSS),Phases=@Value(_fasesDSS),kv=@Value(_basekV),kw=@Value(demandakWdiv2),pf=0.92,Vminpu=0.92,Vmaxpu=1.5,model=2,daily=arqCurvaNorm@Value(TipCrvaCarga),status=variable
        new load.@Value(CodConsBT)M2 bus1=@Value(CodPonAcopl)@Value(_barrasDSS),Phases=@Value(_fasesDSS),kv=@Value(_basekV),kw=@Value(demandakWdiv2),pf=0.92,Vminpu=0.92,Vmaxpu=1.5,model=3,daily=arqCurvaNorm@Value(TipCrvaCarga),status=variable
    -> AttributeRemover
AttributeRemover
    REMOVE_ATTRS = CodConsBT,EnerMedid10_MWh,EnerMedid07_MWh,DO,fatorKtotal,TipCrvaCarga,numSA,EnerMedid02_MWh,EnerMedid11_MWh,_fasesDSS,EnerMedid09_MWh,EnerMedid01_MWh,numDU,SA,CodFas,EnerMedid03_MWh,numDO,EnerMedidMes,_barrasDSS,EnerMedid04_MWh,EnerMedid05_MWh,EnerMedid12_MWh,CodCrvCrg,CodPonAcopl,_basekV,EnerMedid08_MWh,DU,EnerMedid06_MWh
    -> Output (output)
Output (output)

FME custom transformer estConsumoDemanda

Parameters:
- ENERMEDID05_MWH = @Value(EnerMedid05_MWh)   # Enermedid05 Mwh
- ENERMEDID03_MWH = @Value(EnerMedid03_MWh)   # Enermedid03 Mwh
- ENERMEDID12_MWH = @Value(EnerMedid12_MWh)   # Enermedid12 Mwh
- ENERMEDID09_MWH = @Value(EnerMedid09_MWh)   # Enermedid09 Mwh
- DO = @Value(DO)
- ENERMEDID02_MWH = @Value(EnerMedid02_MWh)   # Enermedid02 Mwh
- ENERMEDID01_MWH = @Value(EnerMedid01_MWh)   # Enermedid01 Mwh
- ENERMEDID04_MWH = @Value(EnerMedid04_MWh)   # Enermedid04 Mwh
- ENERMEDID11_MWH = @Value(EnerMedid11_MWh)   # Enermedid11 Mwh
- DU = @Value(DU)
- SA = @Value(SA)
- ENERMEDID06_MWH = @Value(EnerMedid06_MWh)   # Enermedid06 Mwh
- ENERMEDID07_MWH = @Value(EnerMedid07_MWh)   # Enermedid07 Mwh
- ENERMEDID10_MWH = @Value(EnerMedid10_MWh)   # Enermedid10 Mwh
- MESACALCULAR = @Value(mesACalcular)   # mesACalcular
- ENERMEDID08_MWH = @Value(EnerMedid08_MWh)   # Enermedid08 Mwh

AttributeValueMapper_4_Input (input)
    -> AttributeValueMapper_4
Note: numero DU
AttributeValueMapper_4
    LUT = 1,20,2,20,3,22,4,20,5,21,6,22,7,21,8,23,9,21,10,20,11,20,12,22
    DIRECTION = Forward (Source To Destination)
    SRC = mesACalcular
    VAL_ATTR = numDU
    -> AttributeValueMapper_7
Note: numero Sabados
AttributeValueMapper_7
    LUT = 1,5,2,4,3,4,4,5,5,4,6,4,7,5,8,4,9,4,10,5,11,4,12,5
    DIRECTION = Forward (Source To Destination)
    SRC = mesACalcular
    VAL_ATTR = numSA
    -> AttributeValueMapper_8
Note: numero Domingo
AttributeValueMapper_8
    LUT = 1,6,2,5,3,5,4,5,5,6,6,4,7,5,8,4,9,5,10,6,11,6,12,4
    DIRECTION = Forward (Source To Destination)
    SRC = mesACalcular
    VAL_ATTR = numDO
    -> AttributeValueMapper_3
Note: verifica qual o mês será montadoo arquivo
AttributeValueMapper_3
    LUT = 1,@Value(EnerMedid01_MWh),2,@Value(EnerMedid02_MWh),3,@Value(EnerMedid03_MWh),4,@Value(EnerMedid04_MWh),5,@Value(EnerMedid05_MWh),6,@Value(EnerMedid06_MWh),7,@Value(EnerMedid07_MWh),8,@Value(EnerMedid08_MWh),9,@Value(EnerMedid09_MWh),10,@Value(EnerMedid10_MWh),11,@Value(EnerMedid11_MWh),12,@Value(EnerMedid12_MWh)
    DIRECTION = Forward (Source To Destination)
    SRC = mesACalcular
    VAL_ATTR = EnerMedidMes
    -> Tester
Note: verifica se consumo diferente 0
Tester
    TEST_DESCRIPTION = ""
    TEST_MODE = Automatic
    TEST_CLAUSE = TEST @Value(EnerMedidMes) != 0
    BOOL_OP = OR
    PASSED -> AttributeCreator
Note: fator K total
AttributeCreator
    ATTR_TABLE:
      SET_TO fatorKtotal = @add(
        @mult(@Value(DO),@Value(numDO)),
        @mult(@Value(DU),@Value(numDU)),
        @mult(@Value(SA),@Value(numSA))
        )
    -> AttributeCreator_2
Note: demanda kW
AttributeCreator_2
    ATTR_TABLE:
      SET_TO demandaKW = @div( @mult( @Value(EnerMedidMes),1000 ),@Value(fatorKtotal) )
      SET_TO demandakWdiv2 = @div(@Value(demandaKW),2)
    -> AttributeCreator_2_Output (output)
AttributeCreator_2_Output (output)

FME custom transformer escreveRamalBT

Parameters:
- CODFAS = @Value(CodFas)   # CodFas
- CODCOND = @Value(CodCond)   # CodCond
- CODPONACOPL1 = @Value(CodPonAcopl1)   # CodPonAcopl1
- CODPONACOPL2 = @Value(CodPonAcopl2)   # CodPonAcopl2
- CODRMLBT = @Value(CodRmlBT)   # CodRmlBT
- COMP_KM = @Value(Comp_km)   # Comp Km
- CODALIM = @Value(CodAlim)   # CodAlim

Input (input)
    -> AttributeValueMapper_5
Note: barrasDSS
AttributeValueMapper_5
    LUT = AN,.1.0,BN,.1.0,CN,.1.0,ABN,.1.2.0,BCN,.1.2.0,CAN,.1.2.0,ABCN,.1.2.3.0
    DIRECTION = Forward (Source To Destination)
    SRC = CodFas
    VAL_ATTR = _barrasDSS
    -> AttributeValueMapper_6
Note: fasesDSS
AttributeValueMapper_6
    LUT = A,1,B,1,C,1,AB,2,BC,2,CA,2,ABC,3,AN,1,BN,1,CN,1,ABN,2,BCN,2,CAN,2,ABCN,3
    DIRECTION = Forward (Source To Destination)
    SRC = CodFas
    VAL_ATTR = _fasesDSS
    -> StringReplacer
StringReplacer
    REGEXP = NO
    SRC_ATTRS = Comp_km
    REPLACE_TEXT = .
    FIND_TEXT = ,
    NO_MATCH = _FME_NO_OP_
    CASE = NO
    -> AttributeCreator_3
Note: linha DSS
AttributeCreator_3
    ATTR_TABLE = SET_TO text_line_data = new line.@Value(CodRmlBT) bus1=@Value(CodPonAcopl1)@Value(_barrasDSS),bus2=@Value(CodPonAcopl2)@Value(_barrasDSS),Phases=@Value(_fasesDSS),Linecode=@Value(CodCond),Length=@Value(Comp_km),Units=km
    -> AttributeRemover
AttributeRemover
    REMOVE_ATTRS = CodPonAcopl2,CodFas,CodRmlBT,CodCond,_barrasDSS,_fasesDSS,CodPonAcopl1,Comp_km
    -> Output (output)
Output (output)
